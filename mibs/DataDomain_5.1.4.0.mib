-- **********************************************************************
--
-- Copyright 2004-2009 Data Domain, Inc.
-- All Rights Reserved.
--
-- Management Information Base for Data Domain Products
-- 
-- Data Domain enterprise number is 19746
--
-- The ASN.1 prefix to, and including the Data Domain, Inc.  Enterprise is
--      1.3.6.1.4.1.19746
--
-- OBJECT IDENTIFIER's 19746.1-99 reserved for DD SNMP modules
--
-- **********************************************************************

DATA-DOMAIN-MIB DEFINITIONS ::=	BEGIN

    IMPORTS
	MODULE-IDENTITY, OBJECT-TYPE, NOTIFICATION-TYPE, enterprises, Counter32, Integer32, Counter64
	    FROM SNMPv2-SMI
	MODULE-COMPLIANCE, OBJECT-GROUP, NOTIFICATION-GROUP
	    FROM SNMPv2-CONF
    TEXTUAL-CONVENTION
	    FROM SNMPv2-TC
    ifIndex, InterfaceIndex, ifDescr             
            FROM IF-MIB;
        
    dataDomainMib MODULE-IDENTITY
	LAST-UPDATED "201011080000Z"  -- 8 November, 2010
	ORGANIZATION "Data Domain, Inc"
	CONTACT-INFO
	    "Phone: +1-408-980-4800 
	     Fax:   +1-408-980-8620"
	DESCRIPTION
	    "This MIB is used for managing the suite of Data Domain Products."
	REVISION "201011080000Z"  -- 8 November, 2010
	DESCRIPTION
		"Removed nfsStatsAuthenticationFailures."
	::= { enterprises 19746 }

    dataDomainMibConformance	OBJECT IDENTIFIER ::= { dataDomainMib 0 }

    dataDomainMibObjects	OBJECT IDENTIFIER ::= { dataDomainMib 1 }

    dataDomainMibNotifications	OBJECT IDENTIFIER ::= { dataDomainMib 2 }
    
    dataDomainMibProducts	OBJECT IDENTIFIER ::= { dataDomainMib 3 }
    

-- temporary placeholder for autogen header file

    environmentals		OBJECT IDENTIFIER ::= { dataDomainMibObjects 1 }

    nvram			OBJECT IDENTIFIER ::= { dataDomainMibObjects 2 }

    fileSystem			OBJECT IDENTIFIER ::= { dataDomainMibObjects 3 }

    alerts			OBJECT IDENTIFIER ::= { dataDomainMibObjects 4 }

    statistics			OBJECT IDENTIFIER ::= { dataDomainMibObjects 5 }

    diskStorage			OBJECT IDENTIFIER ::= { dataDomainMibObjects 6 }

    replication			OBJECT IDENTIFIER ::= { dataDomainMibObjects 8 }

    nfs			OBJECT IDENTIFIER ::= { dataDomainMibObjects 9 }

    cifs		OBJECT IDENTIFIER ::= { dataDomainMibObjects 10 }

    vtl			OBJECT IDENTIFIER ::= { dataDomainMibObjects 11 }

    ddboost			OBJECT IDENTIFIER ::= { dataDomainMibObjects 12 }

    dataDomainSystem		OBJECT IDENTIFIER ::= { dataDomainMibObjects 13 }

    art                         OBJECT IDENTIFIER ::= { dataDomainMibObjects 14 }

    mtree                       OBJECT IDENTIFIER ::= { dataDomainMibObjects 15 }

    restorer            	OBJECT IDENTIFIER ::= { dataDomainMibProducts 1 }
-- generated platform section for Data Domain MIB
  unknown    OBJECT IDENTIFIER ::= { restorer 0 }
  dd200    OBJECT IDENTIFIER ::= { restorer 1 }
  dd200Proto    OBJECT IDENTIFIER ::= { restorer 2 }
  dd410    OBJECT IDENTIFIER ::= { restorer 3 }
  dd430    OBJECT IDENTIFIER ::= { restorer 4 }
  dd460    OBJECT IDENTIFIER ::= { restorer 5 }
  dd400g    OBJECT IDENTIFIER ::= { restorer 6 }
  dd460g    OBJECT IDENTIFIER ::= { restorer 7 }
  dd560    OBJECT IDENTIFIER ::= { restorer 8 }
  dd560g    OBJECT IDENTIFIER ::= { restorer 9 }
  dd580    OBJECT IDENTIFIER ::= { restorer 10 }
  dd580g    OBJECT IDENTIFIER ::= { restorer 11 }
  dd565    OBJECT IDENTIFIER ::= { restorer 12 }
  dd530    OBJECT IDENTIFIER ::= { restorer 13 }
  dd510    OBJECT IDENTIFIER ::= { restorer 14 }
  dd120    OBJECT IDENTIFIER ::= { restorer 15 }
  dd690    OBJECT IDENTIFIER ::= { restorer 16 }
  dd690g    OBJECT IDENTIFIER ::= { restorer 17 }
  dd660    OBJECT IDENTIFIER ::= { restorer 18 }
  dd880    OBJECT IDENTIFIER ::= { restorer 19 }
  dd880g    OBJECT IDENTIFIER ::= { restorer 20 }
  dd610    OBJECT IDENTIFIER ::= { restorer 21 }
  dd630    OBJECT IDENTIFIER ::= { restorer 22 }
  dd140    OBJECT IDENTIFIER ::= { restorer 23 }
  dd670    OBJECT IDENTIFIER ::= { restorer 24 }
  dd860    OBJECT IDENTIFIER ::= { restorer 25 }
  dd860g    OBJECT IDENTIFIER ::= { restorer 26 }
  dd890    OBJECT IDENTIFIER ::= { restorer 27 }
  dd640    OBJECT IDENTIFIER ::= { restorer 28 }
  dd620    OBJECT IDENTIFIER ::= { restorer 29 }
  dd160    OBJECT IDENTIFIER ::= { restorer 30 }
  vddr    OBJECT IDENTIFIER ::= { restorer 31 }
  unset    OBJECT IDENTIFIER ::= { restorer 9999 }
    -- Generic Type definitions.

    EnclosureID		::= TEXTUAL-CONVENTION
	DISPLAY-HINT	"d"
    STATUS current
    DESCRIPTION
   		"unique Enclosure ID, used as index in several tables"
	SYNTAX	Integer32(1..2147483647)
					

    Temperature		::= TEXTUAL-CONVENTION
	DISPLAY-HINT	"d"
    STATUS current
    DESCRIPTION
   		"Temperature value in Celsius"
	SYNTAX	Integer32

    Minutes		::= TEXTUAL-CONVENTION
	DISPLAY-HINT	"d"
    STATUS current
    DESCRIPTION
   		"Minutes"
	SYNTAX	Integer32

    Percentage		::= TEXTUAL-CONVENTION
	DISPLAY-HINT	"d"
    STATUS current
    DESCRIPTION
   		"Percentage"
	SYNTAX	Integer32(0..100)

    PercentageStr	::= TEXTUAL-CONVENTION
	DISPLAY-HINT	"20a"
    STATUS current
    DESCRIPTION
   		"Percentage string"
	SYNTAX	OCTET STRING  (SIZE (0..20))


    KBytesPerSecond		::= TEXTUAL-CONVENTION
    STATUS current
    DESCRIPTION
   		"Number of KBytes transferred per second"
	SYNTAX	Counter32

    OpsPerSecond		::= TEXTUAL-CONVENTION
    STATUS current
    DESCRIPTION
   		"Number of Operations performed per second"
	SYNTAX	Counter32

    ErrorCount		::= TEXTUAL-CONVENTION
    STATUS current
    DESCRIPTION
   		"Number of Errors Encountered"
	SYNTAX	Counter32

    DDMibTableIndexTC      ::= TEXTUAL-CONVENTION
	DISPLAY-HINT	"d"
    STATUS current
    DESCRIPTION
   		"Index for Any Data Domain MIB table"
	SYNTAX	Integer32(0..2147483647)

    DDMibTableString32TC   ::= TEXTUAL-CONVENTION
	DISPLAY-HINT	"32a"
    STATUS current
    DESCRIPTION
   		"DD Mib Table String 32"
	SYNTAX	OCTET STRING  (SIZE (0..32))

    DDMibTableString64TC   ::= TEXTUAL-CONVENTION
	DISPLAY-HINT	"64a"
    STATUS current
    DESCRIPTION
   		"DD Mib Table String 64"
	SYNTAX	OCTET STRING  (SIZE (0..64))

    DDMibTableString128TC   ::= TEXTUAL-CONVENTION
	DISPLAY-HINT	"128a"
    STATUS current
    DESCRIPTION
   		"DD Mib Table String 128"
	SYNTAX	OCTET STRING  (SIZE (0..128))

    DDMibTableString256TC   ::= TEXTUAL-CONVENTION
	DISPLAY-HINT	"256a"
    STATUS current
    DESCRIPTION
   		"DD Mib Table String 256"
	SYNTAX	OCTET STRING  (SIZE (0..256))


    DDMibTableString512TC   ::= TEXTUAL-CONVENTION
	DISPLAY-HINT	"512a"
    STATUS current
    DESCRIPTION
   		"DD Mib Table String 512"
	SYNTAX	OCTET STRING  (SIZE (0..512))

    DDMibTableString1024TC   ::= TEXTUAL-CONVENTION
	DISPLAY-HINT	"1024a"
    STATUS current
    DESCRIPTION
   		"DD Mib Table String 1024"
	SYNTAX	OCTET STRING  (SIZE (0..1024))

    DDMibTableSizeGibTC ::= TEXTUAL-CONVENTION
    DISPLAY-HINT	"20a"
    STATUS current
    DESCRIPTION
	    "Data Domain Compression size in GiB"
    SYNTAX	OCTET STRING  (SIZE (0..20))

    DDMibRowDescriptionTC		::= TEXTUAL-CONVENTION
	DISPLAY-HINT	"64a"
    STATUS current
    DESCRIPTION
   		"Data Domain Mib Row Description"
	SYNTAX	OCTET STRING  (SIZE (0..64))


    DDMibDateTC		::= TEXTUAL-CONVENTION
	DISPLAY-HINT	"16a"
    STATUS current
    DESCRIPTION
   		"Data Domain Mib Date in the yyyy-mm-dd hh:mm format"
	SYNTAX	OCTET STRING  (SIZE (0..16))

    DDMibMemorySizeTC		::= TEXTUAL-CONVENTION
	DISPLAY-HINT	"d"
    STATUS current
    DESCRIPTION
   		"Data Domain Mib Memory Size of  in bytes."
	SYNTAX	Integer32

    DDMibTimeStampTC		::= TEXTUAL-CONVENTION
	DISPLAY-HINT	"64a"
    STATUS current
    DESCRIPTION
   		"DD Mib Timestamp"
	SYNTAX	OCTET STRING  (SIZE (0..64))
	

    DDMibHostTC ::= TEXTUAL-CONVENTION
	DISPLAY-HINT	"256a"
    STATUS current
    DESCRIPTION
   		"Data Domain Host"
	SYNTAX	OCTET STRING  (SIZE (0..256))

    DDMibPortTC 		::= TEXTUAL-CONVENTION
	DISPLAY-HINT	"256a"
    STATUS current
    DESCRIPTION
   		"Data Domain Port"
	SYNTAX	OCTET STRING  (SIZE (0..256))

    DDMibAlertDescriptionTC		::= TEXTUAL-CONVENTION
	DISPLAY-HINT	"256a"
    STATUS current
    DESCRIPTION
   		"Data Domain Mib Alert Description"
	SYNTAX	OCTET STRING  (SIZE (0..2456))

    DDMibVersionTC		::= TEXTUAL-CONVENTION
	DISPLAY-HINT	"64a"
    STATUS current
    DESCRIPTION
   		"Data Domain Mib version"
	SYNTAX	OCTET STRING  (SIZE (0..64))
	

    DDMibSerialNumberTC		::= TEXTUAL-CONVENTION
	DISPLAY-HINT	"64a"
    STATUS current
    DESCRIPTION
   		"Data Domain Mib Serial Number"
	SYNTAX	OCTET STRING  (SIZE (0..64))

    DDMibTableEnabledTC		::= TEXTUAL-CONVENTION
    STATUS current
    DESCRIPTION
   		"DD Mib Table  Enabled"
    SYNTAX	INTEGER { 
					no		(0),
					yes      	(1)
				    }


    DDMibInteger32TC		::= TEXTUAL-CONVENTION
	DISPLAY-HINT	"d"
    STATUS current
    DESCRIPTION
   		"Data Domain Mib Integer 32."
	SYNTAX	Integer32

    DDMibCompressionFactorTC	    ::= TEXTUAL-CONVENTION
	DISPLAY-HINT	"20a"
    STATUS current
    DESCRIPTION
   		"Data Domain compression factor"
	SYNTAX	OCTET STRING  (SIZE (0..20))

    -- Specific Type definitions.

    PowerModuleIndexTC		::= TEXTUAL-CONVENTION
	DISPLAY-HINT	"d"
    STATUS current
    DESCRIPTION
   		"Number of Power Module present in the DDR"
	SYNTAX	Integer32(0..2147483647)

    PowerModuleDescriptionTC		::= TEXTUAL-CONVENTION
	DISPLAY-HINT	"64a"
    STATUS current
    DESCRIPTION
   		"Power Module Description"
	SYNTAX	OCTET STRING  (SIZE (0..64))

    PowerModuleStatusTC		::= TEXTUAL-CONVENTION
    STATUS current
    DESCRIPTION
   		"Current Power Module Status"
	SYNTAX	INTEGER { 
					absent (0),
					ok		(1),
					failed		(2),
					faulty		(3),
					acnone (4),
					unknown (99)
				    }

    TempSensorIndexTC		::= TEXTUAL-CONVENTION
	DISPLAY-HINT	"d"
    STATUS current
    DESCRIPTION
   		"Number of Temperature Sensor present in the DDR"
	SYNTAX	Integer32(0..2147483647)

    TempSensorDescriptionTC		::= TEXTUAL-CONVENTION
	DISPLAY-HINT	"64a"
    STATUS current
    DESCRIPTION
   		"Temperature Sensor Description"
	SYNTAX	OCTET STRING  (SIZE (0..64))
	
    TempSensorStatusTC		::= TEXTUAL-CONVENTION
    STATUS current
    DESCRIPTION
   		"Current Temperature Sensor Status"
    SYNTAX		INTEGER { 
					failed		(0),
					ok			(1),
					notfound	(2),
					overheatWarning (3),
					overheatCritical (4)
				    }

    FanIndexTC		::= TEXTUAL-CONVENTION
	DISPLAY-HINT	"d"
    STATUS current
    DESCRIPTION
   		"Fan Number of fan that is present in DDR"
	SYNTAX	Integer32(0..2147483647)
	
    FanDescriptionTC		::= TEXTUAL-CONVENTION
	DISPLAY-HINT	"64a"
    STATUS current
    DESCRIPTION
   		"Fan Description"
	SYNTAX	OCTET STRING  (SIZE (0..64))
	

    FanLevelTC		::= TEXTUAL-CONVENTION
    STATUS current
    DESCRIPTION
   		"Current Fan level"
    SYNTAX	INTEGER { 
					unknown	(0), 
					low		(1),
					normal		(2),
					high		(3)
				    }

    FanStatusTC		::= TEXTUAL-CONVENTION
    STATUS current
    DESCRIPTION
   		"Current Fan Status"
    SYNTAX	INTEGER { 
					notfound	(0), 
					ok		(1),
					fail		(2)
				    }

    NvramIndexTC		::= TEXTUAL-CONVENTION
	DISPLAY-HINT	"d"
    STATUS current
    DESCRIPTION
   		"Index of NVRAM card present in the DDR"
	SYNTAX	Integer32(0..2147483647)

    NvramMemorySizeTC		::= TEXTUAL-CONVENTION
	DISPLAY-HINT	"d"
    STATUS current
    DESCRIPTION
   		"Memory Size of NVRAM in bytes."
	SYNTAX	Integer32

    NvramWindowSizeTC		::= TEXTUAL-CONVENTION
	DISPLAY-HINT	"d"
    STATUS current
    DESCRIPTION
   		"Window Size of NVRAM in bytes."
	SYNTAX	Integer32

    NvramBatteryIndexTC		::= TEXTUAL-CONVENTION
	DISPLAY-HINT	"d"
    STATUS current
    DESCRIPTION
   		"Number of NVRAM Battery present in the DDR"
	SYNTAX	Integer32(0..2147483647)

    NvramBatteryStatusTC		::= TEXTUAL-CONVENTION
    STATUS current
    DESCRIPTION
   		"Current NVRAM Battery Status"
    SYNTAX	INTEGER { 
					ok		(0),
					disabled	(1), 
					discharged	(2),
					softdisabled (3)
				    }

    DiskIndexTC		::= TEXTUAL-CONVENTION
	DISPLAY-HINT	"d"
    STATUS current
    DESCRIPTION
   		"Disk Number of disk that is present in the DDR"
	SYNTAX	Integer32(0..2147483647)

    DiskModelTC		::= TEXTUAL-CONVENTION
	DISPLAY-HINT	"64a"
    STATUS current
    DESCRIPTION
   		"Manufacture & Model Number of disk"
	SYNTAX	OCTET STRING  (SIZE (0..64))
	

    DiskFirmwareVersionTC		::= TEXTUAL-CONVENTION
	DISPLAY-HINT	"64a"
    STATUS current
    DESCRIPTION
   		"Firmware version of disk"
	SYNTAX	OCTET STRING  (SIZE (0..64))
	

    DiskSerialNumberTC		::= TEXTUAL-CONVENTION
	DISPLAY-HINT	"64a"
    STATUS current
    DESCRIPTION
   		"Serial Number of disk"
	SYNTAX	OCTET STRING  (SIZE (0..64))
	

    DiskCapacityTC		::= TEXTUAL-CONVENTION
	DISPLAY-HINT	"20a"
    STATUS current
    DESCRIPTION
   		"Capacity of disk"
	SYNTAX	OCTET STRING  (SIZE (0..20))
							
    DiskStateTC		::= TEXTUAL-CONVENTION
    STATUS current
    DESCRIPTION
   		"Current Disk State"
    SYNTAX	INTEGER { 
					ok		(1),
					unknown		(2),
					absent		(3), 
					failed		(4)
				    }
				    
    DiskSectorsPerSecondTC		::= TEXTUAL-CONVENTION
    STATUS current
    DESCRIPTION
   		"Number of disk sectors being transferred per second"
	SYNTAX	Counter32

    FileSystemStatusTC		::= TEXTUAL-CONVENTION
    STATUS current
    DESCRIPTION
   		"Current File System Status"
    SYNTAX	INTEGER { 
					enabled		(1),
					disabled	(2),
					running		(3),
					unknown		(4),
                                        error           (5),
                                        cleaning       (6)
				    }

    FileSystemResourceIndexTC		::= TEXTUAL-CONVENTION
	DISPLAY-HINT	"d"
    STATUS current
    DESCRIPTION
   		"Resource Number of file system resource"
	SYNTAX	Integer32(0..2147483647)

    FileSystemResourceNameTC		::= TEXTUAL-CONVENTION
	DISPLAY-HINT	"64a"
    STATUS current
    DESCRIPTION
   		"File System resource name"
	SYNTAX	OCTET STRING  (SIZE (0..64))
	

    FileSystemSpaceUnitTC		::= TEXTUAL-CONVENTION
    DISPLAY-HINT	"20a"
    STATUS current
    DESCRIPTION
   		"Units of space in the file System represented in Gigabytes"
    SYNTAX	OCTET STRING  (SIZE (0..20))

    
    FileSystemCompressionSizeTC		::= TEXTUAL-CONVENTION
    DISPLAY-HINT	"20a"
    STATUS current
    DESCRIPTION
	    "File Systems Compression size in GiB"
    SYNTAX	OCTET STRING  (SIZE (0..20))


    FileSystemCompressionFactorTC		::= TEXTUAL-CONVENTION
	DISPLAY-HINT	"20a"
    STATUS current
    DESCRIPTION
   		"File System compression factor"
	SYNTAX	OCTET STRING  (SIZE (0..20))

    FileSystemCompressionPeriodTC		::= TEXTUAL-CONVENTION
	DISPLAY-HINT	"20a"
    STATUS current
    DESCRIPTION
   		"File System compression period: last 24 hours, last 7 days"
	SYNTAX	OCTET STRING  (SIZE (0..20))

    DateTC		::= TEXTUAL-CONVENTION
	DISPLAY-HINT	"16a"
    STATUS current
    DESCRIPTION
   		"Date in the yyyy-mm-dd hh:mm format"
	SYNTAX	OCTET STRING  (SIZE (0..16))

    FileSystemOptionsIndexTC ::= TEXTUAL-CONVENTION
    DISPLAY-HINT	"d"
    STATUS current
    DESCRIPTION
        "Index of File System Option Table Index"
    SYNTAX	Integer32(0..2147483647)

    FileSystemOptionsNameTC ::= TEXTUAL-CONVENTION
    DISPLAY-HINT	"128a"
    STATUS current
    DESCRIPTION
        "Index of File Systems Option Name "
    SYNTAX	OCTET STRING  (SIZE (0..128))

    FileSystemOptionsValueTC ::= TEXTUAL-CONVENTION
    DISPLAY-HINT	"128a"
    STATUS current
    DESCRIPTION
        "Index of File Systems Option Value "
    SYNTAX	OCTET STRING  (SIZE (0..128))

    FileSystemCleanIndexTC	    ::= TEXTUAL-CONVENTION
	DISPLAY-HINT	"d"
    STATUS current
    DESCRIPTION
   		"File System Clean Index"
	SYNTAX	Integer32(0..2147483647)
        
    FileSystemCleanStatusTC ::= TEXTUAL-CONVENTION
    DISPLAY-HINT	"128a"
    STATUS current
    DESCRIPTION
        "File System Clean Status "
    SYNTAX	OCTET STRING  (SIZE (0..128))

    FileSystemCleanScheduleTC   ::= TEXTUAL-CONVENTION
    DISPLAY-HINT	"128a"
    STATUS current
    DESCRIPTION
        "File System Clean Schedule "
    SYNTAX	OCTET STRING  (SIZE (0..128))

    FileSystemCleanThrottleTC   ::= TEXTUAL-CONVENTION
    DISPLAY-HINT	"128a"
    STATUS current
    DESCRIPTION
        "File System Clean throttle"
    SYNTAX	OCTET STRING  (SIZE (0..128))



	
    AlertIndexTC		::= TEXTUAL-CONVENTION
	DISPLAY-HINT	"d"
    STATUS current
    DESCRIPTION
   		"Alert Row Index"
	SYNTAX	Integer32(0..2147483647)

    AlertTimestampTC		::= TEXTUAL-CONVENTION
	DISPLAY-HINT	"64a"
    STATUS current
    DESCRIPTION
   		"Alert Timestamp"
	SYNTAX	OCTET STRING  (SIZE (0..64))
	

    AlertDescriptionTC		::= TEXTUAL-CONVENTION
	DISPLAY-HINT	"255a"
    STATUS current
    DESCRIPTION
   		"Alert Description"
	SYNTAX	OCTET STRING  (SIZE (0..255))
	
    
    SystemStatsIndexTC		::= TEXTUAL-CONVENTION
	DISPLAY-HINT	"d"
    STATUS current
    DESCRIPTION
   		"Statistics Row Index"
	SYNTAX	Integer32(0..2147483647)

    RaidDiskStateTC		::= TEXTUAL-CONVENTION
    STATUS current
    DESCRIPTION
   		"Raid Disk State"
    SYNTAX	INTEGER { 
					inuse		(1),
					notinuse	(2),
					spare		(3),
					absent		(4),
					failed		(5),
					invalid	(6),
					foreign	(7),
					known	(8),
                                        available (9),
					unknown		(99)
				    }

    RaidDiskStatusTC		::= TEXTUAL-CONVENTION
	DISPLAY-HINT	"64a"
    STATUS current
    DESCRIPTION
   		"extra status string of Raid Disk Group node"
	SYNTAX	OCTET STRING  (SIZE (0..64))

    RaidDiskGroupTC		::= TEXTUAL-CONVENTION
	DISPLAY-HINT	"64a"
    STATUS current
    DESCRIPTION
   		"Name of Raid Disk Group"
	SYNTAX	OCTET STRING  (SIZE (0..64))
	

    ReplicationStateTC		::= TEXTUAL-CONVENTION
    STATUS current
    DESCRIPTION
   		"Current Replication status"
    SYNTAX	INTEGER { 
					enabled		(1),
					disabled	(2),
					disabledNeedsResync	(3) 
				    }

    ReplicationStatusTC		::= TEXTUAL-CONVENTION
    STATUS current
    DESCRIPTION
   		"Current Replication connection status"
    SYNTAX	INTEGER { 
					connected		(1),
					disconnected	(2), 
					migrating		(3), 
					suspended		(4), 
					neverConnected	(5)
				    }

    ReplicationConnectTimeTC		::= TEXTUAL-CONVENTION
	DISPLAY-HINT	"d"
    STATUS current
    DESCRIPTION
   		"timestamp when connection was established, or 0 if there is no Replication connection"
	SYNTAX	Integer32

    ReplicationPathTC		::= TEXTUAL-CONVENTION
	DISPLAY-HINT	"254a"
    STATUS current
    DESCRIPTION
   		"source or destination path for replication"
	SYNTAX	OCTET STRING  (SIZE (0..254))
	
    ReplicationTrafficTC		::= TEXTUAL-CONVENTION
    STATUS current
    DESCRIPTION
   		"measurement of bytes being replicated"
	SYNTAX	Counter64

    ReplicationThrottleTC		::= TEXTUAL-CONVENTION
	DISPLAY-HINT	"d"
    STATUS current
    DESCRIPTION
   		"measurement of replication throttle in bps"
	SYNTAX	Integer32

    ReplicationSyncedTimeTC		::= TEXTUAL-CONVENTION
	DISPLAY-HINT	"d"
    STATUS current
    DESCRIPTION
   		"timestamp when replication source and destination were in sync, or 0 if unknown"
	SYNTAX	Integer32
					
    ReplicationContextTC		::= TEXTUAL-CONVENTION
	DISPLAY-HINT	"d"
    STATUS current
    DESCRIPTION
   		"0 for collection replication contexts, > 0 for directory replication contexts"
	SYNTAX	Integer32(0..2147483647)


    ReplicationConfigIndexTC	::= TEXTUAL-CONVENTION
	DISPLAY-HINT	"d"
    STATUS current
    DESCRIPTION
   		"Replication Config Row Index"
	SYNTAX	Integer32(0..2147483647)


    ReplicationConfigContextIdTC    ::= TEXTUAL-CONVENTION
	DISPLAY-HINT	"32a"
    STATUS current
    DESCRIPTION
   		"Replicaton Configuration Context Id"
	SYNTAX	OCTET STRING  (SIZE (0..32))

    ReplicationConfigSourceTC   ::= TEXTUAL-CONVENTION
	DISPLAY-HINT	"256a"
    STATUS current
    DESCRIPTION
   		"Replicaton Configuration Connection Source"
	SYNTAX	OCTET STRING  (SIZE (0..256))

    ReplicationConfigDestTC     ::= TEXTUAL-CONVENTION
	DISPLAY-HINT	"256a"
    STATUS current
    DESCRIPTION
   		"Replicaton Configuration Destination"
	SYNTAX	OCTET STRING  (SIZE (0..256))

    ReplicationConfigConnHostTC     ::= TEXTUAL-CONVENTION
	DISPLAY-HINT	"256a"
    STATUS current
    DESCRIPTION
   		"Replicaton Configuration Connection Host"
	SYNTAX	OCTET STRING  (SIZE (0..256))

    ReplicationConfigConnPortTC 		::= TEXTUAL-CONVENTION
	DISPLAY-HINT	"256a"
    STATUS current
    DESCRIPTION
   		"Replicaton Configuration Connection Port"
	SYNTAX	OCTET STRING  (SIZE (0..256))

  

    ReplicationConfigLowBWOptimTC		::= TEXTUAL-CONVENTION
    STATUS current
    DESCRIPTION
   		"Replication Low BW Optimization Status"
    SYNTAX	INTEGER { 
					disabled	(0),
					enabled 	(1)
				    }


    ReplicationConfigEnabledTC		::= TEXTUAL-CONVENTION
    STATUS current
    DESCRIPTION
   		"Replication Configuration Enabled"
    SYNTAX	INTEGER { 
					no		(0),
					yes      	(1)
				    }



					
    NfsStatusTC		::= TEXTUAL-CONVENTION
    STATUS current
    DESCRIPTION
   		"Current Network File System Status"
    SYNTAX	INTEGER { 
					enabled		(1),
					disabled	(2)
				    }

    NfsClientIndexTC		::= TEXTUAL-CONVENTION
	DISPLAY-HINT	"d"
    STATUS current
    DESCRIPTION
   		"Index of NFS clients"
	SYNTAX	Integer32(0..2147483647)

    NfsClientPathTC		::= TEXTUAL-CONVENTION
	DISPLAY-HINT	"1024a"
    STATUS current
    DESCRIPTION
   		"NFS path"
	SYNTAX	OCTET STRING  (SIZE (0..1024))

    NfsClientClientsTC		::= TEXTUAL-CONVENTION
	DISPLAY-HINT	"1024a"
    STATUS current
    DESCRIPTION
   		"NFS Clients"
	SYNTAX	OCTET STRING  (SIZE (0..1024))

    NfsClientOptionsTC		::= TEXTUAL-CONVENTION
	DISPLAY-HINT	"254a"
    STATUS current
    DESCRIPTION
   		"NFS options"
	SYNTAX	OCTET STRING  (SIZE (0..254))

    NfsStatsIndexTC		::= TEXTUAL-CONVENTION
	DISPLAY-HINT	"d"
    STATUS current
    DESCRIPTION
   		"Index of NFS stats"
	SYNTAX	Integer32(0..2147483647)

    NfsStatsExportPointTC		::= TEXTUAL-CONVENTION
	DISPLAY-HINT	"254a"
    STATUS current
    DESCRIPTION
   		"NFS export point"
	SYNTAX	OCTET STRING  (SIZE (0..254))

    NfsStatsFilesystemTypeTC		::= TEXTUAL-CONVENTION
	DISPLAY-HINT	"32a"
    STATUS current
    DESCRIPTION
   		"NFS file system type"
	SYNTAX	OCTET STRING  (SIZE (0..32))

    NfsStatsCacheEntryTC	::= TEXTUAL-CONVENTION
    STATUS current
    DESCRIPTION
   		"Number of cache entries"
	SYNTAX  Counter32	

    NfsStatsFileHandleLookupTC	::= TEXTUAL-CONVENTION
    STATUS current
    DESCRIPTION
   		"Number of file handle lookup"
	SYNTAX  Counter32	

    NfsStatsMaxCacheSizeTC	::= TEXTUAL-CONVENTION
    STATUS current
    DESCRIPTION
   		"Max cache size"
	SYNTAX  Counter32	

    NfsStatsCurrentOpenStreamsTC    ::= TEXTUAL-CONVENTION
    STATUS current
    DESCRIPTION
   		"Number of current open streams"
	SYNTAX  Counter32	

    VtlAdminStateTC		::= TEXTUAL-CONVENTION
    STATUS current
    DESCRIPTION
   		"Current VTL administration state"
    SYNTAX	INTEGER { 
					unknown	    (0),
					enabled		(1),
					disabled	(2),
					failed	    (3)
				    }

    VtlProcessStateTC		::= TEXTUAL-CONVENTION
    STATUS current
    DESCRIPTION
   		"Current VTL process state"
    SYNTAX	INTEGER { 
					unknown		(0),
					stopped		(1),
					starting	(2),
					running	    (3),
					timingout   (4),
					stopping    (5),
					stuck       (6)
				    }

    VtlLibraryIndexTC		::= TEXTUAL-CONVENTION
    STATUS current
    DESCRIPTION
   		"Index of VTL library"
	SYNTAX  Integer32(0..64)	

    VtlLibraryNameTC		::= TEXTUAL-CONVENTION
	DISPLAY-HINT	"64a"
    STATUS current
    DESCRIPTION
   		"VTL library name"
	SYNTAX	OCTET STRING  (SIZE (0..64))

    VtlLibraryVendorTC		::= TEXTUAL-CONVENTION
	DISPLAY-HINT	"64a"
    STATUS current
    DESCRIPTION
   		"VTL library vendor"
	SYNTAX	OCTET STRING  (SIZE (0..64))

    VtlLibraryModelTC		::= TEXTUAL-CONVENTION
	DISPLAY-HINT	"64a"
    STATUS current
    DESCRIPTION
   		"VTL library model"
	SYNTAX	OCTET STRING  (SIZE (0..64))

    VtlLibraryRevisionTC		::= TEXTUAL-CONVENTION
	DISPLAY-HINT	"64a"
    STATUS current
    DESCRIPTION
   		"VTL library revision"
	SYNTAX	OCTET STRING  (SIZE (0..64))

    VtlLibrarySerialTC		::= TEXTUAL-CONVENTION
	DISPLAY-HINT	"64a"
    STATUS current
    DESCRIPTION
   		"VTL library serial"
	SYNTAX	OCTET STRING  (SIZE (0..64))

    VtlLibraryTotalDrivesTC    ::= TEXTUAL-CONVENTION
    STATUS current
    DESCRIPTION
   		"Number of VTL drives"
	SYNTAX  Counter32	

    VtlLibraryTotalSlotsTC    ::= TEXTUAL-CONVENTION
    STATUS current
    DESCRIPTION
   		"Number of VTL slots"
	SYNTAX  Counter32	

    VtlLibraryTotalCapsTC    ::= TEXTUAL-CONVENTION
    STATUS current
    DESCRIPTION
   		"Number of VTL caps"
	SYNTAX  Counter32	

    VtlLibraryStatusTC    ::= TEXTUAL-CONVENTION
    STATUS current
    DESCRIPTION
   		"Current VTL library status"
	SYNTAX	INTEGER { 
			unknown	(0), 
			online	(1),
			offline	(2)
			}

    VtlDriveIndexTC		::= TEXTUAL-CONVENTION
    STATUS current
    DESCRIPTION
   		"Index of VTL drive"
	SYNTAX  Integer32(0..512) 

    VtlDriveNameTC		::= TEXTUAL-CONVENTION
	DISPLAY-HINT	"64a"
    STATUS current
    DESCRIPTION
   		"VTL drive name"
	SYNTAX	OCTET STRING  (SIZE (0..64))

    VtlDriveVendorTC		::= TEXTUAL-CONVENTION
	DISPLAY-HINT	"64a"
    STATUS current
    DESCRIPTION
   		"VTL drive vendor"
	SYNTAX	OCTET STRING  (SIZE (0..64))

    VtlDriveModelTC		::= TEXTUAL-CONVENTION
	DISPLAY-HINT	"64a"
    STATUS current
    DESCRIPTION
   		"VTL drive model"
	SYNTAX	OCTET STRING  (SIZE (0..64))

    VtlDriveRevisionTC		::= TEXTUAL-CONVENTION
	DISPLAY-HINT	"64a"
    STATUS current
    DESCRIPTION
   		"VTL drive revision"
	SYNTAX	OCTET STRING  (SIZE (0..64))

    VtlDriveSerialTC		::= TEXTUAL-CONVENTION
	DISPLAY-HINT	"64a"
    STATUS current
    DESCRIPTION
   		"VTL drive serial"
	SYNTAX	OCTET STRING  (SIZE (0..64))

    VtlDriveStatusTC    ::= TEXTUAL-CONVENTION
    STATUS current
    DESCRIPTION
   		"Current VTL drive status"
	SYNTAX	INTEGER { 
			unknown	(0), 
			online	(1),
			offline	(2)
			}

    VtlDriveTapeVolumeTC		::= TEXTUAL-CONVENTION
	DISPLAY-HINT	"64a"
    STATUS current
    DESCRIPTION
   		"VTL drive tape volume"
	SYNTAX	OCTET STRING  (SIZE (0..64))

    VtlPortIndexTC	        	::= TEXTUAL-CONVENTION
    STATUS current
    DESCRIPTION
   		"VTL Port Table Index"
	SYNTAX Integer32(0..10) 	

    VtlPortNameTC                       ::= TEXTUAL-CONVENTION
	DISPLAY-HINT	"32a"
    STATUS current
    DESCRIPTION
   		"VTL Port Name "
	SYNTAX	OCTET STRING  (SIZE (0..32))

    VtlPortIDTC	                	::= TEXTUAL-CONVENTION
    STATUS current
    DESCRIPTION
   		"VTL Port Id"
	SYNTAX	Counter32

    VtlPortModelTC		::= TEXTUAL-CONVENTION
	DISPLAY-HINT	"32a"
    STATUS current
    DESCRIPTION
   		"VTL Port MODEL"
	SYNTAX	OCTET STRING  (SIZE (0..32))

    VtlPortFirmwareTC		::= TEXTUAL-CONVENTION
	DISPLAY-HINT	"32a"
    STATUS current
    DESCRIPTION
   		"VTL Port Firmware"
	SYNTAX	OCTET STRING  (SIZE (0..32))

    VtlPortWWNNTC		::= TEXTUAL-CONVENTION
	DISPLAY-HINT	"64a"
    STATUS current
    DESCRIPTION
   		"VTL WWNN Address"
	SYNTAX	OCTET STRING  (SIZE (0..64))

    VtlPortWWPNTC		::= TEXTUAL-CONVENTION
	DISPLAY-HINT	"64a"
    STATUS current
    DESCRIPTION
   		"VTL WWPN Address"
	SYNTAX	OCTET STRING  (SIZE (0..64))

    VtlPortConnectionTypeTC	::= TEXTUAL-CONVENTION
    STATUS current
    DESCRIPTION
   		"VTL Port Connection Type"
	SYNTAX	INTEGER { 
                    n-PORT	    (0), 
                    loop	    (1),
                    point-to-Point  (2),
                    fabric-Loop     (3),
                    unknown         (4)
                }


    VtlPortSpeedTC		::= TEXTUAL-CONVENTION
    STATUS current
    DESCRIPTION
   		"VTL Port Speed "
	SYNTAX	INTEGER { 
                    zero-GBPS       (0), 
                    one-GBPS	    (1),
                    two-GBPS        (2),
                    three-GBPS      (3),
                    four-GBPS       (4),
                    eight-GBPS      (5),
                    unknown         (6)
                }

    VtlPortEnabledTC		::= TEXTUAL-CONVENTION
    STATUS current
    DESCRIPTION
   		"VTL Port Enabled"
	SYNTAX	INTEGER {
                    disabled        (0),
                    enabled         (1),
                    unknown         (2)
                }

    
    VtlPortStatusTC		::= TEXTUAL-CONVENTION
    STATUS current
    DESCRIPTION
   		"VTL Port State"
	SYNTAX	INTEGER {
                    offline         (0),
                    online          (1),
                    uknown          (2)
                }

        
    VtlTapeIndexTC	       	::= TEXTUAL-CONVENTION
    STATUS current
    DESCRIPTION
   		"VTL Tape Table Index"
	SYNTAX  Integer32(0..250000)	

    VtlTapeBarCodeTC                ::= TEXTUAL-CONVENTION
	DISPLAY-HINT	"64a"
    STATUS current
    DESCRIPTION
   		"VTL Tape Bar Code "
	SYNTAX	OCTET STRING  (SIZE (0..64))

    VtlTapePoolTC                ::= TEXTUAL-CONVENTION
	DISPLAY-HINT	"32a"
    STATUS current
    DESCRIPTION
   		"VTL Tape Pool "
	SYNTAX	OCTET STRING  (SIZE (0..32))

    VtlTapeLocationTC                ::= TEXTUAL-CONVENTION
	DISPLAY-HINT	"32a"
    STATUS current
    DESCRIPTION
   		"VTL Tape Location "
	SYNTAX	OCTET STRING  (SIZE (0..32))
    
    VtlTapeStateTC                ::= TEXTUAL-CONVENTION
	DISPLAY-HINT	"32a"
    STATUS current
    DESCRIPTION
   		"VTL Tape State "
	SYNTAX	OCTET STRING  (SIZE (0..32))
    
    VtlTapeSizeTC                ::= TEXTUAL-CONVENTION
	DISPLAY-HINT	"32a"
    STATUS current
    DESCRIPTION
   		"VTL Tape Size "
	SYNTAX	OCTET STRING  (SIZE (0..32))
    
    VtlTapeUsedTC                ::= TEXTUAL-CONVENTION
	DISPLAY-HINT	"32a"
    STATUS current
    DESCRIPTION
   		"VTL Tape Used "
	SYNTAX	OCTET STRING  (SIZE (0..32))
    
    VtlTapeCompTC                ::= TEXTUAL-CONVENTION
	DISPLAY-HINT	"32a"
    STATUS current
    DESCRIPTION
   		"VTL Tape Compression "
	SYNTAX	OCTET STRING  (SIZE (0..32))

    VtlTapeModTimeTC                ::= TEXTUAL-CONVENTION
	DISPLAY-HINT	"32a"
    STATUS current
    DESCRIPTION
   		"VTL Tape Mod Time "
	SYNTAX	OCTET STRING  (SIZE (0..32))

        
    VtlStatsIndexTC	       	::= TEXTUAL-CONVENTION
    STATUS current
    DESCRIPTION
   		"VTL Stats Table Index"
	SYNTAX  Integer32(0..2147483647)	

    VtlStatsPortTC                ::= TEXTUAL-CONVENTION
	DISPLAY-HINT	"32a"
    STATUS current
    DESCRIPTION
   		"VTL Tape Bar Code "
	SYNTAX	OCTET STRING  (SIZE (0..32))

    
    VtlStatsConrolCommandsTC        ::= TEXTUAL-CONVENTION
    STATUS current
    DESCRIPTION
   		"VTL Stats Table Control Commands"
	SYNTAX 	Counter64

    VtlStatsWriteCommandsTC         ::= TEXTUAL-CONVENTION
    STATUS current
    DESCRIPTION
   		"VTL Stats Table write commands"
	SYNTAX 	Counter64

    VtlStatsReadCommandsTC	       	::= TEXTUAL-CONVENTION
    STATUS current
    DESCRIPTION
   		"VTL Stats Table Read Commands"
	SYNTAX 	Counter64

    VtlStatsInTC                            ::= TEXTUAL-CONVENTION
    STATUS current
    DESCRIPTION
   		"VTL Stats Table Stats In"
	SYNTAX 	Counter64

    VtlStatsOutTC                           ::= TEXTUAL-CONVENTION
    STATUS current
    DESCRIPTION
   		"VTL Stats Table Stats Out"
	SYNTAX 	Counter64

    VtlStatsLinkFailuresTC	       	::= TEXTUAL-CONVENTION
    STATUS current
    DESCRIPTION
   		"VTL Stats Table Link failures"
	SYNTAX 	Counter64

    VtlStatsLIPCountTC	       	::= TEXTUAL-CONVENTION
    STATUS current
    DESCRIPTION
   		"VTL Stats Table LIP count"
	SYNTAX 	Counter64

    VtlStatsSyncLossesTC	       	::= TEXTUAL-CONVENTION
    STATUS current
    DESCRIPTION
   		"VTL Stats Table Sync Losses"
	SYNTAX 	Counter64

    VtlStatsSignalLossesTC         	       	::= TEXTUAL-CONVENTION
    STATUS current
    DESCRIPTION
   		"VTL Stats Table Signal Losses"
	SYNTAX 	Counter64

    VtlStatsPrimSeqProtoErrorsTC                ::= TEXTUAL-CONVENTION
    STATUS current
    DESCRIPTION
   		"VTL Stats Table Prim Seq Protocol Errors"
	SYNTAX 	Counter64

    VtlStatsInvalidTxWordsTC               ::= TEXTUAL-CONVENTION
    STATUS current
    DESCRIPTION
   		"VTL Stats Table Invalid Tx Words"
	SYNTAX 	Counter64

    VtlStatsInvalidCRCsTC               ::= TEXTUAL-CONVENTION
    STATUS current
    DESCRIPTION
   		"VTL Stats Table Invalid CRCs"
	SYNTAX 	Counter64



    CifsStatusTC		::= TEXTUAL-CONVENTION
    STATUS current
    DESCRIPTION
   		"Current CIFS status"
    SYNTAX	INTEGER { 
					enabled		             (1),
                    enabled-running          (2),
                    enabled-not-running      (3),
                    enabled-windbind-not-run (4),
					disabled	             (5)
				    }

    CifsConfigModeTC		::= TEXTUAL-CONVENTION
	DISPLAY-HINT	"64a"
    STATUS current
    DESCRIPTION
   		"Current CIFS mode"
	SYNTAX	OCTET STRING  (SIZE (0..64))

    CifsConfigWINSServerTC		::= TEXTUAL-CONVENTION
	DISPLAY-HINT	"1024a"
    STATUS current
    DESCRIPTION
   		"CIFS WINS servers"
	SYNTAX	OCTET STRING  (SIZE (0..1024))

    CifsConfigNetBIOSHostnameTC		::= TEXTUAL-CONVENTION
	DISPLAY-HINT	"255a"
    STATUS current
    DESCRIPTION
   		"CIFS NetBIOS hostname"
	SYNTAX	OCTET STRING  (SIZE (0..255))

    CifsConfigDomainControllerTC		::= TEXTUAL-CONVENTION
	DISPLAY-HINT	"1024a"
    STATUS current
    DESCRIPTION
   		"CIFS Domain Controller"
	SYNTAX	OCTET STRING  (SIZE (0..1024))

    CifsConfigDNSTC		::= TEXTUAL-CONVENTION
	DISPLAY-HINT	"1024a"
    STATUS current
    DESCRIPTION
   		"CIFS DNS server"
	SYNTAX	OCTET STRING  (SIZE (0..1024))

    CifsConfigGroupNameTC		::= TEXTUAL-CONVENTION
	DISPLAY-HINT	"255a"
    STATUS current
    DESCRIPTION
   		"CIFS group name"
	SYNTAX	OCTET STRING  (SIZE (0..255))

    CifsShareIndexTC		::= TEXTUAL-CONVENTION
	DISPLAY-HINT	"d"
    STATUS current
    DESCRIPTION
   		"Index of CIFS share"
	SYNTAX	Integer32(0..2147483647)

    CifsShareNameTC		::= TEXTUAL-CONVENTION
	DISPLAY-HINT	"255a"
    STATUS current
    DESCRIPTION
   		"CIFS share name"
	SYNTAX	OCTET STRING  (SIZE (0..255))

    CifsSharePathTC		::= TEXTUAL-CONVENTION
	DISPLAY-HINT	"1024a"
    STATUS current
    DESCRIPTION
   		"CIFS share path"
	SYNTAX	OCTET STRING  (SIZE (0..1024))

    CifsShareMaxConnectionTC    ::= TEXTUAL-CONVENTION
    STATUS current
    DESCRIPTION
   		"CIFS maximum connection"
	SYNTAX  Counter32

    CifsShareClientsTC		::= TEXTUAL-CONVENTION
	DISPLAY-HINT	"1024a"
    STATUS current
    DESCRIPTION
   		"CIFS share clients"
	SYNTAX	OCTET STRING  (SIZE (0..1024))

    CifsShareBrowsingTC		::= TEXTUAL-CONVENTION
    STATUS current
    DESCRIPTION
   		"Current CIFS browsing"
    SYNTAX	INTEGER { 
					enabled		             (1),
					disabled	             (2)
				    }

    CifsShareWriteableTC		::= TEXTUAL-CONVENTION
    STATUS current
    DESCRIPTION
   		"Current CIFS writeable"
    SYNTAX	INTEGER { 
					enabled		             (1),
					disabled	             (2)
				    }

    CifsShareUserTC		::= TEXTUAL-CONVENTION
	DISPLAY-HINT	"1024a"
    STATUS current
    DESCRIPTION
   		"CIFS share user"
	SYNTAX	OCTET STRING  (SIZE (0..1024))

    CifsShareCommentTC		::= TEXTUAL-CONVENTION
	DISPLAY-HINT	"255a"
    STATUS current
    DESCRIPTION
   		"CIFS share comment"
	SYNTAX	OCTET STRING  (SIZE (0..255))

    CifsStatsSummaryIndexTC         ::= TEXTUAL-CONVENTION
    DISPLAY-HINT	"d"
    STATUS current
    DESCRIPTION
        "Index of Cifs Stats Summary Table"
    SYNTAX	Integer32(0..2147483647)

    CifsStatsSummaryTotalOpsTC ::= TEXTUAL-CONVENTION
    DISPLAY-HINT	"d"
    STATUS current
    DESCRIPTION
        "Index of CIFS Stats Details Total Ops Count"
    SYNTAX	Counter32

    CifsStatsSummarySMBTotalReadsTC  ::= TEXTUAL-CONVENTION
    DISPLAY-HINT	"d"
    STATUS current
    DESCRIPTION
        "Index of CIFS Stats  SMB Total Reads"
    SYNTAX	Counter32

    CifsStatsSummarySMBTotalWritesTC ::= TEXTUAL-CONVENTION
    DISPLAY-HINT	"d"
    STATUS current
    DESCRIPTION
        "Index of CIFS Stats Summary Total Writes "
    SYNTAX	Counter32


    CifsStatsDetailsIndexTC ::= TEXTUAL-CONVENTION
    DISPLAY-HINT	"d"
    STATUS current
    DESCRIPTION
        "Index of CIFS Stats Details Table"
    SYNTAX	Integer32(0..2147483647)

    CifsStatsDetailsOperationTC ::= TEXTUAL-CONVENTION
    DISPLAY-HINT	"d"
    STATUS current
    DESCRIPTION
        "Index of CIFS Stats Details Total count"
    SYNTAX	Counter32
    
    CifsStatsDetailsCountTC ::= TEXTUAL-CONVENTION
    DISPLAY-HINT	"d"
    STATUS current
    DESCRIPTION
        "Index of CIFS Stats Details Count"
    SYNTAX	Counter32
    
    CifsStatsDetailsTimeTC ::= TEXTUAL-CONVENTION
    DISPLAY-HINT	"d"
    STATUS current
    DESCRIPTION
        "Index of CIFS Stats Details Time in ms"
    SYNTAX	Counter32
    
    CifsStatsDetailsTimePercentTC ::= TEXTUAL-CONVENTION
    DISPLAY-HINT	"20a"
    STATUS current
    DESCRIPTION
        "Index of CIFS Stats Details Time in percentage"
    SYNTAX	OCTET STRING  (SIZE (0..20))


    CifsOptionsIndexTC ::= TEXTUAL-CONVENTION
    DISPLAY-HINT	"d"
    STATUS current
    DESCRIPTION
        "Index of CIFS Option Table Index"
    SYNTAX Integer32(0..100)
    
    CifsOptionsNameTC ::= TEXTUAL-CONVENTION
    DISPLAY-HINT	"128a"
    STATUS current
    DESCRIPTION
        "Index of CIFS Option Name "
    SYNTAX	OCTET STRING  (SIZE (0..128))
    
    CifsOptionsValueTC ::= TEXTUAL-CONVENTION
    DISPLAY-HINT	"128a"
    STATUS current
    DESCRIPTION
        "Index of CIFS Option Value "
    SYNTAX	OCTET STRING  (SIZE (0..128))
    

    DDboostStatsIndexTC		::= TEXTUAL-CONVENTION
    DISPLAY-HINT	"d"
    STATUS current
    DESCRIPTION
        "Index of ddboost Stats Table"
    SYNTAX	Integer32(0..2147483647)

         
    DDboostStatusTC		        ::= TEXTUAL-CONVENTION
    STATUS current
    DESCRIPTION
               "DDboost Status"
    SYNTAX	INTEGER     { 
                                  enabled	(1),
                                  disabled	(2)
                            }

   
    DDboostUserTC		::= TEXTUAL-CONVENTION
    DISPLAY-HINT	"1024a"
    STATUS current
    DESCRIPTION
            "DDboost user"
    SYNTAX	OCTET STRING  (SIZE (0..1024))

    SystemSerialNumberTC                                ::= TEXTUAL-CONVENTION
	DISPLAY-HINT	"128a"
    STATUS current
    DESCRIPTION
   		"System Serial Number"
	SYNTAX	OCTET STRING  (SIZE (0..128))

    FileSystemArchiveUnitStateTC		        ::= TEXTUAL-CONVENTION
    STATUS current
    DESCRIPTION
               "File System Archive Unit State"
    SYNTAX	INTEGER     { 
                                  new	(1),
                                  target	(2),
                                  sealed   (3)
                            }

    FileSystemArchiveUnitStatusTC		        ::= TEXTUAL-CONVENTION
    STATUS current
    DESCRIPTION
               "File System Archive Unit Status"
    SYNTAX	INTEGER     { 
                                  ready	(1),
                                  disabled	(2)
                            }

    MtreeListStatusTC		        ::= TEXTUAL-CONVENTION
    STATUS current
    DESCRIPTION
               "Mtree List  Status TC"
    SYNTAX	INTEGER     { 
                                  deleted	(1),
                                  readOnly     (2),
                                  readWrite    (3),
                                  replicationDestination  (4),
                                  retention-LockEnabled   (5),
                                  retention-LockDisabled  (6)
                            }
    MtreeRetentionLockStatusTC        ::= TEXTUAL-CONVENTION
    STATUS current
    DESCRIPTION
               "Mtree Retention Lock"
    SYNTAX	INTEGER     { 
                                  enabled	(1),
                                  disabled	(2)
                            }


-- **********************************************************************
--
-- DataDomainMibCompliance 
-- =======================
--
-- dataDomainMib			(1.3.6.1.4.1.19746)
--   dataDomainMibConformance		(1.3.6.1.4.1.19746.0)
--	dataDomainMibComplicances	(1.3.6.1.4.1.19746.0.1)
--	    dataDoamainMibCompliance	(1.3.6.1.4.1.19746.0.1.1)
--
-- **********************************************************************

    dataDomainMibCompliances	OBJECT IDENTIFIER ::= { dataDomainMibConformance 1 }

    dataDomainMibCompliance MODULE-COMPLIANCE
	STATUS  current
	DESCRIPTION
	    "The compliance statement for SNMP entities which
	    implement this MIB module."
	MODULE  -- this module
	    MANDATORY-GROUPS { environmentalsGroup, nvramGroup, fileSystemGroup, alertsGroup, statisticsGroup, 
			       replGroup, nfsGroup, cifsGroup, vtlGroup }

	    GROUP   internalDiskStorageGroup
	    DESCRIPTION
		"This group is mandatory for SNMP entities which
		support internal disk storage"

	    GROUP   externalUnmanagedDiskStorageGroup
	    DESCRIPTION
		"This group is mandatory for SNMP entities which
		support external unmanaged disk storage"

    ::= { dataDomainMibCompliances 1 }

-- **********************************************************************
--
-- DataDomainMibCompliance 
-- =======================
--
-- dataDomainMib			(1.3.6.1.4.1.19746)
--   dataDomainMibConformance		(1.3.6.1.4.1.19746.0)
--	dataDoamainMibGroups		(1.3.6.1.4.1.19746.0.2)
--
-- **********************************************************************

    dataDomainMibGroups		OBJECT IDENTIFIER ::= { dataDomainMibConformance 2 }

    environmentalsGroup OBJECT-GROUP
	OBJECTS {
	    powerModuleDescription,
	    powerModuleStatus,
	    tempSensorDescription,
	    tempSensorCurrentValue,
	    tempSensorStatus,
	    fanDescription,
	    fanLevel,
	    fanStatus
	}
	STATUS  current
	DESCRIPTION
            "A collection of objects providing environmental monitoring information."
	::= { dataDomainMibGroups 1 }

    nvramGroup OBJECT-GROUP
	OBJECTS {
	    nvramMemorySize,
	    nvramWindowSize,
	    nvramPCIErrorCount,
	    nvramMemoryErrorCount,
	    nvramBatteryStatus,
	    nvramBatteryCharge 
	}
	STATUS  current
	DESCRIPTION
            "A collection of objects providing nvram monitoring information."
	::= { dataDomainMibGroups 2 }

    fileSystemGroup OBJECT-GROUP
	OBJECTS {
	    fileSystemStatus,
	    fileSystemVirtualSpace,
	    fileSystemResourceName,
	    fileSystemSpaceSize,
	    fileSystemSpaceUsed,
	    fileSystemSpaceAvail,
	    fileSystemPercentUsed,
            fileSystemSpaceCleanable,
	    fileSystemCompressionPeriod,
	    fileSystemCompressionStartTime,
	    fileSystemCompressionEndTime,
	    fileSystemPreCompressionSize,
	    fileSystemPostCompressionSize,
	    fileSystemGlobalCompressionFactor,
	    fileSystemLocalCompressionFactor,
            fileSystemTotalCompressionFactor,
            fileSystemReductionPercent
	}
	STATUS  current
	DESCRIPTION
            "A collection of objects providing file system monitoring information."
	::= { dataDomainMibGroups 3 }

    alertsGroup OBJECT-GROUP
	OBJECTS {
	    currentAlertTimestamp,
	    currentAlertDescription
	}
	STATUS  current
	DESCRIPTION
            "A collection of objects providing alert monitoring information."
	::= { dataDomainMibGroups 4 }

    statisticsGroup OBJECT-GROUP
	OBJECTS {
	    cpuAvgPercentageBusy,
	    cpuMaxPercentageBusy,
	    nfsOpsPerSecond,
	    nfsIdlePercentage,
	    nfsProcPercentage,
	    nfsSendPercentage,
	    nfsReceivePercentage,
	    cifsOpsPerSecond,
	    diskReadKBytesPerSecond,
	    diskWriteKBytesPerSecond,
	    diskBusyPercentage,
	    nvramReadKBytesPerSecond,
	    nvramWriteKBytesPerSecond,
	    replInKBytesPerSecond,
	    replOutKBytesPerSecond
	}
	STATUS  current
	DESCRIPTION
            "A collection of objects providing statistics information."
	::= { dataDomainMibGroups 5 }

    internalDiskStorageGroup OBJECT-GROUP
	OBJECTS {
	    diskModel,
	    diskFirmwareVersion,
	    diskSerialNumber,
	    diskCapacity,
	    diskPropState,
	    diskSectorsRead,
	    diskSectorsWritten,
	    diskTotalKBytes,
	    diskBusy,
	    diskPerfState,
	    diskTemperature,
	    diskTimeoutCount,
	    diskReadFailCount,
	    diskWriteFailCount,
	    diskMiscFailCount,
	    diskOffTrackErrCount,
	    diskSoftEccCount,
	    diskCrcErrCount,
	    diskProbationalCount,
	    diskReallocCount,
	    diskErrState
	}
	STATUS  current
	DESCRIPTION
            "A collection of objects providing internal disk monitoring information."
	::= { dataDomainMibGroups 7 }

    externalUnmanagedDiskStorageGroup OBJECT-GROUP
	OBJECTS {
	    diskModel,
	    diskFirmwareVersion,
	    diskSerialNumber,
	    diskCapacity,
	    diskPropState,
	    diskSectorsRead,
	    diskSectorsWritten,
	    diskTotalKBytes,
	    diskBusy,
	    diskPerfState
	}
	STATUS  current
	DESCRIPTION
            "A collection of objects providing external unmanaged disk monitoring information."
	::= { dataDomainMibGroups 8 }

    basicNotificationsGroup NOTIFICATION-GROUP
	NOTIFICATIONS {
	    powerSupplyFailedAlarm,
	    systemOverheatWarningAlarm,
	    systemOverheatAlertAlarm,
	    systemOverheatShutdownAlarm,
	    fanModuleFailedAlarm,
	    nvramFailingAlarm,
	    fileSystemFailedAlarm,
	    fileSpaceMaintenanceAlarm,
	    fileSpacePreWarningAlarm,
	    fileSpaceWarningAlarm,
	    fileSpaceSevereAlarm,
	    fileSpaceCriticalAlarm,
	    diskOverheatWarningAlarm, 
	    diskOverheatAlertAlarm, 
	    diskOverheatShutdownAlarm, 
	    diskFailedAlarm, 
	    diskNoSpareAlarm, 
	    diskPathAlarm, 
	    diskSASAlarm, 
	    diskSASHBAAlarm, 
	    snapshotFullAlarm, 
	    snapshotHWMAlarm, 
	    clusterNodeAlarm, 
	    clusterInterfaceAlarm, 
	    replSyncAlarm, 
	    systemStartupAlarm, 
	    filesysRelaunchAlarm, 
	    filesysDDGCFailedAlarm, 
	    filesysGeneralProblemAlarm, 
	    diskUnsupportedAlarm,
            eventIPMIUnmanageAlarm
	}
	STATUS  deprecated 
	DESCRIPTION
            "A collection of objects providing basic notifications."
	::= { dataDomainMibGroups 9 }

    internalDiskStorageNotificationsGroup NOTIFICATION-GROUP
	NOTIFICATIONS {
	    diskFailedAlarm,
	    diskOverheatWarningAlarm,
	    diskOverheatAlertAlarm,
	    diskOverheatShutdownAlarm
	}
	STATUS deprecated 
	DESCRIPTION
            "A collection of objects providing internal disk storage notifications."
	::= { dataDomainMibGroups 10 }

	replGroup OBJECT-GROUP
	OBJECTS {
		replState,
		replStatus,
		replFileSysStatus,
		replConnTime,
		replSource, 
		replDestination,
		replPreCompBytesSent,
		replPostCompBytesSent,
		replPreCompBytesRemaining,
		replPostCompBytesReceived,
		replThrottle,
		replSyncedAsOfTime
	}
	STATUS	current
	DESCRIPTION
		"a collection of objects providing replication pair config and monitoring information."
	::= { dataDomainMibGroups 11 }
	
    nfsGroup OBJECT-GROUP
	OBJECTS {
	    nfsStatus,
	    nfsClientPath,
	    nfsClientClients,
	    nfsClientOptions,
	    nfsStatsExportPoint,
	    nfsStatsFilesystemType,
	    nfsStatsCacheEntry,
	    nfsStatsFileHandleLookup,
	    nfsStatsMaxCacheSize,
	    nfsStatsCurrentOpenStreams
	}
	STATUS  current
	DESCRIPTION
            "A collection of objects providing NFS monitoring information."
	::= { dataDomainMibGroups 12 }

    cifsGroup OBJECT-GROUP
	OBJECTS {
	    cifsStatus,
	    cifsConfigMode,
	    cifsConfigWINSServer,
	    cifsConfigNetBIOSHostname,
	    cifsConfigDomainController,
	    cifsConfigDNS,
	    cifsConfigGroupName,
	    cifsShareName,
	    cifsSharePath,
	    cifsShareClients,
	    cifsShareUser,
	    cifsShareComment,
	    cifsShareBrowsing,
	    cifsShareWriteable,
	    cifsShareMaxConnection
	}
	STATUS  current
	DESCRIPTION
            "A collection of objects providing CIFS monitoring information."
	::= { dataDomainMibGroups 13 }

    vtlGroup OBJECT-GROUP
	OBJECTS {
	    vtlAdminState,
	    vtlProcessState,
	    vtlLibraryName,
	    vtlLibraryVendor,
	    vtlLibraryModel,
	    vtlLibraryRevision,
	    vtlLibrarySerial,
	    vtlLibraryTotalDrives,
	    vtlLibraryTotalSlots,
	    vtlLibraryTotalCaps,
	    vtlLibraryStatus,
	    vtlDriveName,
	    vtlDriveVendor,
	    vtlDriveModel,
	    vtlDriveRevision,
	    vtlDriveSerial,
	    vtlDriveLibraryName,
	    vtlDriveStatus,
	    vtlDriveTapeVolume
	}
	STATUS  current
	DESCRIPTION
            "A collection of objects providing VTL monitoring information."
	::= { dataDomainMibGroups 14 }

-- **********************************************************************
--
-- Environmentals 
-- ==============
--
-- dataDomainMib		(1.3.6.1.4.1.19746)
--   dataDomainMibObjects	(1.3.6.1.4.1.19746.1)
--	environmentals		(1.3.6.1.4.1.19746.1.1)
--
-- **********************************************************************

-- **********************************************************************
--
-- Power 
-- ============
--
-- dataDomainMib		(1.3.6.1.4.1.19746)
--   dataDomainMibObjects	(1.3.6.1.4.1.19746.1)
--	environmentals		(1.3.6.1.4.1.19746.1.1)
--	    power			(1.3.6.1.4.1.19746.1.1.1)
--
-- **********************************************************************

    power	    OBJECT IDENTIFIER ::= { environmentals 1 }

-- **********************************************************************
--
-- powerModules 
-- ==================
--
-- dataDomainMib        		(1.3.6.1.4.1.19746)
--   dataDomainMibObjects		(1.3.6.1.4.1.19746.1)
--	environmentals			(1.3.6.1.4.1.19746.1.1)
--	    power				(1.3.6.1.4.1.19746.1.1.1)
--	       powerModules		(1.3.6.1.4.1.19746.1.1.1.1)
--
-- **********************************************************************

    powerModules	    OBJECT IDENTIFIER ::= { power 1 }

    powerModuleTable OBJECT-TYPE
        SYNTAX  SEQUENCE OF PowerModuleEntry
        MAX-ACCESS  not-accessible
        STATUS  current
        DESCRIPTION
            "A table containing entries of PowerModuleEntry."
        ::= { powerModules 1 }

    powerModuleEntry OBJECT-TYPE
        SYNTAX  PowerModuleEntry
        MAX-ACCESS  not-accessible
        STATUS  current
        DESCRIPTION "powerModuleTable Row Description" 
        INDEX { powerEnclosureID, powerModuleIndex }
        ::= { powerModuleTable 1 }

    PowerModuleEntry ::= SEQUENCE {
    powerEnclosureID		EnclosureID,
    powerModuleIndex		PowerModuleIndexTC,
    powerModuleDescription  PowerModuleDescriptionTC,
	powerModuleStatus		PowerModuleStatusTC
    }

    powerEnclosureID OBJECT-TYPE
        SYNTAX  EnclosureID
        MAX-ACCESS  not-accessible
        STATUS  current
        DESCRIPTION
            "Power Module Enclosure ID"
        ::= { powerModuleEntry 1 }

    powerModuleIndex OBJECT-TYPE
        SYNTAX  PowerModuleIndexTC
        MAX-ACCESS  not-accessible
        STATUS  current
        DESCRIPTION
            "Power Module index"
        ::= { powerModuleEntry 2 }

    powerModuleDescription OBJECT-TYPE
        SYNTAX  PowerModuleDescriptionTC
        MAX-ACCESS  read-only
        STATUS  current
        DESCRIPTION "Power Module Description"
        ::= { powerModuleEntry 3 }

    powerModuleStatus OBJECT-TYPE
        SYNTAX  PowerModuleStatusTC
        MAX-ACCESS  read-only
        STATUS  current
        DESCRIPTION
            "current enclosure Power Module status"
        ::= { powerModuleEntry 4 }

-- **********************************************************************
--
-- Temperatures 
-- ============
--
-- dataDomainMib		(1.3.6.1.4.1.19746)
--   dataDomainMibObjects	(1.3.6.1.4.1.19746.1)
--	environmentals		(1.3.6.1.4.1.19746.1.1)
--	    temperatures	(1.3.6.1.4.1.19746.1.1.2)
--
-- **********************************************************************

    temperatures	    OBJECT IDENTIFIER ::= { environmentals 2 }

-- **********************************************************************
--
-- TemperatureSensors 
-- ==================
--
-- dataDomainMib        		(1.3.6.1.4.1.19746)
--   dataDomainMibObjects		(1.3.6.1.4.1.19746.1)
--	environmentals			(1.3.6.1.4.1.19746.1.1)
--	    temperatures		(1.3.6.1.4.1.19746.1.1.2)
--	       temperatureSensors	(1.3.6.1.4.1.19746.1.1.2.1)
--
-- **********************************************************************

    temperatureSensors	    OBJECT IDENTIFIER ::= { temperatures 1 }

    temperatureSensorTable OBJECT-TYPE
        SYNTAX  SEQUENCE OF TemperatureSensorEntry
        MAX-ACCESS  not-accessible
        STATUS  current
        DESCRIPTION
            "A table containing entries of TemperatureSensorEntry."
        ::= { temperatureSensors 1 }

    temperatureSensorEntry OBJECT-TYPE
        SYNTAX  TemperatureSensorEntry
        MAX-ACCESS  not-accessible
        STATUS  current
        DESCRIPTION "temperatureSensorTable Row Description" 
        INDEX { tempEnclosureID, tempSensorIndex }
        ::= { temperatureSensorTable 1 }

    TemperatureSensorEntry ::= SEQUENCE {
    tempEnclosureID		EnclosureID,
	tempSensorIndex		TempSensorIndexTC,
        tempSensorTrapIndex     TempSensorIndexTC,
	tempSensorDescription	TempSensorDescriptionTC,
	tempSensorCurrentValue	Temperature,
	tempSensorStatus		TempSensorStatusTC
    }

    tempEnclosureID OBJECT-TYPE
        SYNTAX  EnclosureID
        MAX-ACCESS  not-accessible
        STATUS  current
        DESCRIPTION
            "Temperature Sensor Enclosure ID"
        ::= { temperatureSensorEntry 1 }

    tempSensorIndex OBJECT-TYPE
        SYNTAX  TempSensorIndexTC
        MAX-ACCESS  not-accessible
        STATUS  current
        DESCRIPTION
            "Temperature Sensor Number"
        ::= { temperatureSensorEntry 2 }

    tempSensorTrapIndex OBJECT-TYPE
        SYNTAX  TempSensorIndexTC
        MAX-ACCESS  read-only
        STATUS  current
        DESCRIPTION
            "Temperature Sensor Number Used for Traps"
        ::= { temperatureSensorEntry 3 }

    tempSensorDescription OBJECT-TYPE
        SYNTAX  TempSensorDescriptionTC
        MAX-ACCESS  read-only
        STATUS  current
        DESCRIPTION "Temperature Sensor Description"
        ::= { temperatureSensorEntry 4 }

    tempSensorCurrentValue OBJECT-TYPE
        SYNTAX  Temperature 
        MAX-ACCESS  read-only
        STATUS  current
        DESCRIPTION "Current Temperature Value of the sensor"
        ::= { temperatureSensorEntry 5 }

    tempSensorStatus OBJECT-TYPE
        SYNTAX  TempSensorStatusTC 
        MAX-ACCESS  read-only
        STATUS  current
        DESCRIPTION "Current status of the sensor"
        ::= { temperatureSensorEntry 6 }

-- **********************************************************************
--
-- Fans 
-- ====
--
-- dataDomainMib		(1.3.6.1.4.1.19746)
--   dataDomainMibObjects	(1.3.6.1.4.1.19746.1)
--	environmentals		(1.3.6.1.4.1.19746.1.1)
--	    fans		(1.3.6.1.4.1.19746.1.1.3)
--
-- **********************************************************************

    fans		    OBJECT IDENTIFIER ::= { environmentals 3 }

-- **********************************************************************
--
-- FanProperties
-- =============
--
-- dataDomainMib        	(1.3.6.1.4.1.19746)
--   dataDomainMibObjects	(1.3.6.1.4.1.19746.1)
--	environmentals		(1.3.6.1.4.1.19746.1.1)
--	    fans		(1.3.6.1.4.1.19746.1.1.3)
--		fanProperties	(1.3.6.1.4.1.19746.1.1.3.1)
--
-- **********************************************************************

    fanProperties	    OBJECT IDENTIFIER ::= { fans 1 }

    fanPropertiesTable OBJECT-TYPE
        SYNTAX  SEQUENCE OF FanPropertiesEntry
        MAX-ACCESS  not-accessible
        STATUS  current
        DESCRIPTION
            "A table containing entries of FanPropertiesEntry."
        ::= { fanProperties 1 }

    fanPropertiesEntry OBJECT-TYPE
        SYNTAX  FanPropertiesEntry
        MAX-ACCESS  not-accessible
        STATUS  current
        DESCRIPTION "fanPropertiesTable Row Description" 
        INDEX { fanEnclosureID, fanIndex }
        ::= { fanPropertiesTable 1 }

    FanPropertiesEntry ::= SEQUENCE {
	fanEnclosureID	EnclosureID,
	fanIndex	FanIndexTC,
        fanTrapIndex	FanIndexTC,
	fanDescription  FanDescriptionTC,
	fanLevel	FanLevelTC,
	fanStatus	FanStatusTC
    }

    fanEnclosureID OBJECT-TYPE
        SYNTAX  EnclosureID
        MAX-ACCESS  not-accessible
        STATUS  current
        DESCRIPTION
            "Enclosure ID of fan"
        ::= { fanPropertiesEntry 1 }

    fanIndex OBJECT-TYPE
        SYNTAX  FanIndexTC
        MAX-ACCESS  not-accessible
        STATUS  current
        DESCRIPTION
            "Fan Number"
        ::= { fanPropertiesEntry 2 }

    fanTrapIndex OBJECT-TYPE
        SYNTAX  FanIndexTC
        MAX-ACCESS  read-only
        STATUS  current
        DESCRIPTION
            "Fan Number"
        ::= { fanPropertiesEntry 3 }

    fanDescription OBJECT-TYPE
        SYNTAX  FanDescriptionTC
        MAX-ACCESS  read-only
        STATUS  current
        DESCRIPTION "Vendor supplied description of the fan"
        ::= { fanPropertiesEntry 4 }

    fanLevel OBJECT-TYPE
        SYNTAX  FanLevelTC 
        MAX-ACCESS  read-only
        STATUS  current
        DESCRIPTION "current run level of fan"
        ::= { fanPropertiesEntry 5 }

    fanStatus OBJECT-TYPE
        SYNTAX  FanStatusTC 
        MAX-ACCESS  read-only
        STATUS  current
        DESCRIPTION "Current status of the fan"
        ::= { fanPropertiesEntry 6 }

-- **********************************************************************
--
-- NvramProperties
-- ===============
--
-- dataDomainMib        		(1.3.6.1.4.1.19746)
--   dataDomainMibObjects		(1.3.6.1.4.1.19746.1)
--	nvram				(1.3.6.1.4.1.19746.1.2)
--	    nvramProperties		(1.3.6.1.4.1.19746.1.2.1)
--
-- **********************************************************************

    nvramProperties	    OBJECT IDENTIFIER ::= { nvram 1 }

    nvramPropertiesTable OBJECT-TYPE
        SYNTAX  SEQUENCE OF NvramPropertiesEntry
        MAX-ACCESS  not-accessible
        STATUS  current
        DESCRIPTION
            "A table containing entries of NvramPropertiesEntry."
        ::= { nvramProperties 1 }

    nvramPropertiesEntry OBJECT-TYPE
        SYNTAX  NvramPropertiesEntry
        MAX-ACCESS  not-accessible
        STATUS  current
        DESCRIPTION "nvramPropertiesTable Row Description" 
        INDEX { nvramPropertiesIndex }
        ::= { nvramPropertiesTable 1 }

    NvramPropertiesEntry ::= SEQUENCE {
	nvramPropertiesIndex   NvramIndexTC,
	nvramMemorySize  NvramMemorySizeTC,
	nvramWindowSize  NvramWindowSizeTC 
    }

    nvramPropertiesIndex OBJECT-TYPE
        SYNTAX  NvramIndexTC
        MAX-ACCESS  not-accessible
        STATUS  current
        DESCRIPTION
            "NVRAM card index"
        ::= { nvramPropertiesEntry 1 }

    nvramMemorySize OBJECT-TYPE
        SYNTAX  NvramMemorySizeTC 
        MAX-ACCESS  read-only
        STATUS  current
        DESCRIPTION "Size of NVRAM Memory in bytes"
        ::= { nvramPropertiesEntry 2 }

    nvramWindowSize OBJECT-TYPE
        SYNTAX  NvramWindowSizeTC 
        MAX-ACCESS  read-only
        STATUS  current
        DESCRIPTION "Window size of NVRAM in bytes"
        ::= { nvramPropertiesEntry 3 }

-- **********************************************************************
--
-- NvramStats
-- ==========
--
-- dataDomainMib        		(1.3.6.1.4.1.19746)
--   dataDomainMibObjects		(1.3.6.1.4.1.19746.1)
--	nvram				(1.3.6.1.4.1.19746.1.2)
--	    nvramStats			(1.3.6.1.4.1.19746.1.2.2)
--
-- **********************************************************************

    nvramStats		    OBJECT IDENTIFIER ::= { nvram 2 }

    nvramStatsTable OBJECT-TYPE
        SYNTAX  SEQUENCE OF NvramStatsEntry
        MAX-ACCESS  not-accessible
        STATUS  current
        DESCRIPTION
            "A table containing entries of NvramStatsEntry."
        ::= { nvramStats 1 }

    nvramStatsEntry OBJECT-TYPE
        SYNTAX  NvramStatsEntry
        MAX-ACCESS  not-accessible
        STATUS  current
        DESCRIPTION "nvramStatsTable Row Description" 
        INDEX { nvramStatsIndex }
        ::= { nvramStatsTable 1 }

    NvramStatsEntry ::= SEQUENCE {
	nvramStatsIndex   NvramIndexTC,
	nvramPCIErrorCount  ErrorCount,
	nvramMemoryErrorCount  ErrorCount 
    }

    nvramStatsIndex OBJECT-TYPE
        SYNTAX  NvramIndexTC
        MAX-ACCESS  not-accessible
        STATUS  current
        DESCRIPTION
            "NVRAM card index"
        ::= { nvramStatsEntry 1 }

    nvramPCIErrorCount OBJECT-TYPE
        SYNTAX  ErrorCount 
        MAX-ACCESS  read-only
        STATUS  current
        DESCRIPTION "Number of PCI Errors Encountered on NVRAM Card"
        ::= { nvramStatsEntry 2 }

    nvramMemoryErrorCount OBJECT-TYPE
        SYNTAX  ErrorCount 
        MAX-ACCESS  read-only
        STATUS  current
        DESCRIPTION "Number of Memory Errors  Encountered on NVRAM Card"
        ::= { nvramStatsEntry 3 }

-- **********************************************************************
--
-- NvramBatteries
-- ==============
--
-- dataDomainMib        		(1.3.6.1.4.1.19746)
--   dataDomainMibObjects		(1.3.6.1.4.1.19746.1)
--	nvram				(1.3.6.1.4.1.19746.1.2)
--	    nvramBatteries		(1.3.6.1.4.1.19746.1.2.3)
--
-- **********************************************************************

    nvramBatteries	    OBJECT IDENTIFIER ::= { nvram 3 }

    nvramBatteryTable OBJECT-TYPE
        SYNTAX  SEQUENCE OF NvramBatteryEntry
        MAX-ACCESS  not-accessible
        STATUS  current
        DESCRIPTION
            "A table containing entries of NvramBatteryEntry."
        ::= { nvramBatteries 1 }

    nvramBatteryEntry OBJECT-TYPE
        SYNTAX  NvramBatteryEntry
        MAX-ACCESS  not-accessible
        STATUS  current
        DESCRIPTION "nvramBatteryTable Row Description" 
        INDEX { nvramBatteriesIndex, nvramBatteryIndex }
        ::= { nvramBatteryTable 1 }

    NvramBatteryEntry ::= SEQUENCE {
	nvramBatteriesIndex   NvramIndexTC,
	nvramBatteryIndex   NvramBatteryIndexTC,
	nvramBatteryStatus  NvramBatteryStatusTC,
	nvramBatteryCharge  Percentage 
    }

    nvramBatteriesIndex OBJECT-TYPE
        SYNTAX  NvramIndexTC
        MAX-ACCESS  not-accessible
        STATUS  current
        DESCRIPTION
            "NVRAM card index"
        ::= { nvramBatteryEntry 1 }

    nvramBatteryIndex OBJECT-TYPE
        SYNTAX  NvramBatteryIndexTC
        MAX-ACCESS  not-accessible
        STATUS  current
        DESCRIPTION
            "NVRAM Battery Number"
        ::= { nvramBatteryEntry 2 }

    nvramBatteryStatus OBJECT-TYPE
        SYNTAX  NvramBatteryStatusTC
        MAX-ACCESS  read-only
        STATUS  current
        DESCRIPTION
            "NVRAM Battery Status"
        ::= { nvramBatteryEntry 3 }

    nvramBatteryCharge OBJECT-TYPE
        SYNTAX  Percentage 
        MAX-ACCESS  read-only
        STATUS  current
        DESCRIPTION
            "NVRAM Battery charge percentage"
        ::= { nvramBatteryEntry 4 }

-- **********************************************************************
--
-- FileSystemProperties 
-- ====================
--
-- dataDomainMib        		(1.3.6.1.4.1.19746)
--   dataDomainMibObjects		(1.3.6.1.4.1.19746.1)
--	fileSystem			(1.3.6.1.4.1.19746.1.3)
--	    fileSystemProperties	(1.3.6.1.4.1.19746.1.3.1)
--
-- **********************************************************************

    fileSystemProperties    OBJECT IDENTIFIER ::= { fileSystem 1 }

    fileSystemStatus OBJECT-TYPE
        SYNTAX  FileSystemStatusTC 
        MAX-ACCESS  read-only
        STATUS  current
        DESCRIPTION "Status of the file system"
        ::= { fileSystemProperties 1 }

    fileSystemVirtualSpace OBJECT-TYPE
        SYNTAX  FileSystemSpaceUnitTC 
        MAX-ACCESS  read-only
        STATUS  current
        DESCRIPTION "Amount of Uncompressed data that has been backed up by the system"
        ::= { fileSystemProperties 2 }

-- **********************************************************************
--
-- FileSystemSpace 
-- ===============
--
-- dataDomainMib        		(1.3.6.1.4.1.19746)
--   dataDomainMibObjects		(1.3.6.1.4.1.19746.1)
--	fileSystem			(1.3.6.1.4.1.19746.1.3)
--	    fileSystemSpace		(1.3.6.1.4.1.19746.1.3.2)
--
-- **********************************************************************

    fileSystemSpace	    OBJECT IDENTIFIER ::= { fileSystem 2 }

    fileSystemSpaceTable OBJECT-TYPE
        SYNTAX  SEQUENCE OF FileSystemSpaceEntry
        MAX-ACCESS  not-accessible
        STATUS  current
        DESCRIPTION
            "A table containing entries of FileSystemSpaceEntry."
        ::= { fileSystemSpace 1 }

    fileSystemSpaceEntry OBJECT-TYPE
        SYNTAX  FileSystemSpaceEntry
        MAX-ACCESS  not-accessible
        STATUS  current
        DESCRIPTION 
	    "fileSystemSpaceTable Row Description" 
        INDEX { fileSystemResourceIndex }
        ::= { fileSystemSpaceTable 1 }

    FileSystemSpaceEntry ::= SEQUENCE {
	fileSystemResourceIndex	FileSystemResourceIndexTC,
        fileSystemResourceTrapIndex	FileSystemResourceIndexTC,
	fileSystemResourceName	FileSystemResourceNameTC,
	fileSystemSpaceSize	FileSystemSpaceUnitTC,
	fileSystemSpaceUsed	FileSystemSpaceUnitTC,
	fileSystemSpaceAvail	FileSystemSpaceUnitTC,
	fileSystemPercentUsed		Percentage,
        fileSystemSpaceCleanable    FileSystemSpaceUnitTC
    }

    fileSystemResourceIndex OBJECT-TYPE
        SYNTAX  FileSystemResourceIndexTC 
        MAX-ACCESS  not-accessible
        STATUS  current
        DESCRIPTION
            "File system resource index"
        ::= { fileSystemSpaceEntry 1 }

    fileSystemResourceTrapIndex OBJECT-TYPE
        SYNTAX  FileSystemResourceIndexTC 
        MAX-ACCESS  read-only
        STATUS  current
        DESCRIPTION
            "File system resource trap index"
        ::= { fileSystemSpaceEntry 2 }

    fileSystemResourceName OBJECT-TYPE
        SYNTAX  FileSystemResourceNameTC 
        MAX-ACCESS  read-only
        STATUS  current
        DESCRIPTION
            "File system resource name"
        ::= { fileSystemSpaceEntry 3 }

    fileSystemSpaceSize OBJECT-TYPE
        SYNTAX  FileSystemSpaceUnitTC 
        MAX-ACCESS  read-only
        STATUS  current
        DESCRIPTION
            "Size of the file system resource in gigabytes"
        ::= { fileSystemSpaceEntry 4 }

    fileSystemSpaceUsed OBJECT-TYPE
        SYNTAX  FileSystemSpaceUnitTC 
        MAX-ACCESS  read-only
        STATUS  current
        DESCRIPTION
            "Amount of used space within the file system resource in gigabytes"
        ::= { fileSystemSpaceEntry 5 }

    fileSystemSpaceAvail OBJECT-TYPE
        SYNTAX  FileSystemSpaceUnitTC 
        MAX-ACCESS  read-only
        STATUS  current
        DESCRIPTION
            "Amount of available space within the file system resource in gigabytes"
        ::= { fileSystemSpaceEntry 6 }

    fileSystemPercentUsed OBJECT-TYPE
        SYNTAX  Percentage
        MAX-ACCESS  read-only
        STATUS  current
        DESCRIPTION
            "Percentage of used space within the file system resource"
        ::= { fileSystemSpaceEntry 7 }

    fileSystemSpaceCleanable OBJECT-TYPE
        SYNTAX  FileSystemSpaceUnitTC
        MAX-ACCESS  read-only
        STATUS  current
        DESCRIPTION
            "Amount of cleanable space within the file system resource"
        ::= { fileSystemSpaceEntry 8 }

-- **********************************************************************
--
-- FileSystemCompression 
-- ===============
--
-- dataDomainMib        		(1.3.6.1.4.1.19746)
--   dataDomainMibObjects		(1.3.6.1.4.1.19746.1)
--	fileSystem			        (1.3.6.1.4.1.19746.1.3)
--	    fileSystemCompression   (1.3.6.1.4.1.19746.1.3.3)
--
-- **********************************************************************

    fileSystemCompression	    OBJECT IDENTIFIER ::= { fileSystem 3 }

    fileSystemCompressionTable OBJECT-TYPE
        SYNTAX  SEQUENCE OF FileSystemCompressionEntry
        MAX-ACCESS  not-accessible
        STATUS  current
        DESCRIPTION
            "A table containing entries of FileSystemCompressionEntry."
        ::= { fileSystemCompression 1 }

    fileSystemCompressionEntry OBJECT-TYPE
        SYNTAX  FileSystemCompressionEntry
        MAX-ACCESS  not-accessible
        STATUS  current
        DESCRIPTION 
	    "fileSystemCompressionTable Row Description" 
        INDEX { fileSystemCompressionIndex }
        ::= { fileSystemCompressionTable 1 }

    FileSystemCompressionEntry ::= SEQUENCE {
	fileSystemCompressionIndex			FileSystemResourceIndexTC,
	fileSystemCompressionPeriod			FileSystemCompressionPeriodTC,
	fileSystemCompressionStartTime		DateTC,
	fileSystemCompressionEndTime		DateTC,
	fileSystemPreCompressionSize		FileSystemCompressionSizeTC,
	fileSystemPostCompressionSize		FileSystemCompressionSizeTC,
	fileSystemGlobalCompressionFactor	FileSystemCompressionFactorTC,
	fileSystemLocalCompressionFactor	FileSystemCompressionFactorTC,
        fileSystemTotalCompressionFactor        FileSystemCompressionFactorTC,
        fileSystemReductionPercent              Percentage,
        fileSystemReductionPercent1             PercentageStr 
    }

    fileSystemCompressionIndex OBJECT-TYPE
        SYNTAX  FileSystemResourceIndexTC 
        MAX-ACCESS  not-accessible
        STATUS  current
        DESCRIPTION
            "File system compression index"
        ::= { fileSystemCompressionEntry 1 }

    fileSystemCompressionPeriod OBJECT-TYPE
        SYNTAX  FileSystemCompressionPeriodTC 
        MAX-ACCESS  read-only
        STATUS  current
        DESCRIPTION
            "File system compression period"
        ::= { fileSystemCompressionEntry 2 }

    fileSystemCompressionStartTime OBJECT-TYPE
        SYNTAX  DateTC 
        MAX-ACCESS  read-only
        STATUS  current
        DESCRIPTION
            "File system compression start time"
        ::= { fileSystemCompressionEntry 3 }

    fileSystemCompressionEndTime OBJECT-TYPE
        SYNTAX  DateTC 
        MAX-ACCESS  read-only
        STATUS  current
        DESCRIPTION
            "File system compression end time"
        ::= { fileSystemCompressionEntry 4 }

    fileSystemPreCompressionSize OBJECT-TYPE
        SYNTAX  FileSystemCompressionSizeTC 
        MAX-ACCESS  read-only
        STATUS  current
        DESCRIPTION
            "Size of the file system pre compression in gigabytes"
        ::= { fileSystemCompressionEntry 5 }

    fileSystemPostCompressionSize OBJECT-TYPE
        SYNTAX  FileSystemCompressionSizeTC 
        MAX-ACCESS  read-only
        STATUS  current
        DESCRIPTION
            "Size of the file system post compression in gigabytes"
        ::= { fileSystemCompressionEntry 6 }

    fileSystemGlobalCompressionFactor OBJECT-TYPE
        SYNTAX  FileSystemCompressionFactorTC 
        MAX-ACCESS  read-only
        STATUS  current
        DESCRIPTION
            "File system global compression factor"
        ::= { fileSystemCompressionEntry 7 }

    fileSystemLocalCompressionFactor OBJECT-TYPE
        SYNTAX  FileSystemCompressionFactorTC 
        MAX-ACCESS  read-only
        STATUS  current
        DESCRIPTION
            "File system local compression factor"
        ::= { fileSystemCompressionEntry 8 }

    fileSystemTotalCompressionFactor OBJECT-TYPE
        SYNTAX  FileSystemCompressionFactorTC 
        MAX-ACCESS  read-only
        STATUS  current
        DESCRIPTION
            "File system Total compression factor"
        ::= { fileSystemCompressionEntry 9 }

    fileSystemReductionPercent OBJECT-TYPE
        SYNTAX  Percentage 
        MAX-ACCESS  read-only
        STATUS  deprecated
        DESCRIPTION
            "File system Reduction Percent"
        ::= { fileSystemCompressionEntry 10 }

    fileSystemReductionPercent1 OBJECT-TYPE
        SYNTAX  PercentageStr 
        MAX-ACCESS  read-only
        STATUS  current
        DESCRIPTION
            "File system Reduction Percent"
        ::= { fileSystemCompressionEntry 11 }

-- **********************************************************************
--
-- fileSystemClean
-- ====================
--
-- dataDomainMib                (1.3.6.1.4.1.19746)
--   dataDomainMibObjects       (1.3.6.1.4.1.19746.1)
--     fileSystem                     (1.3.6.1.4.1.19746.1.3)
--       fileSystemClean              (1.3.6.1.4.1.19746.1.3.5)
--
-- **********************************************************************

    fileSystemClean		    OBJECT IDENTIFIER ::= { fileSystem 5 }

    fileSystemCleanTable OBJECT-TYPE
        SYNTAX  SEQUENCE OF FileSystemCleanEntry
        MAX-ACCESS  not-accessible
        STATUS  current
        DESCRIPTION
            "A table containing entries of fileSystemCleanEntry."
        ::= { fileSystemClean 1 }

    fileSystemCleanEntry OBJECT-TYPE
        SYNTAX  FileSystemCleanEntry
        MAX-ACCESS  not-accessible
        STATUS  current
        DESCRIPTION
        "fileSystemCleanTable Row Description"
        INDEX { fileSystemCleanIndex }
        ::= { fileSystemCleanTable 1 }

    FileSystemCleanEntry ::= SEQUENCE {
        fileSystemCleanIndex          FileSystemCleanIndexTC,
        fileSystemCleanStatus           FileSystemCleanStatusTC,
        fileSystemCleanSchedule          FileSystemCleanScheduleTC,
        fileSystemCleanThrottle          FileSystemCleanThrottleTC
    }

    fileSystemCleanIndex OBJECT-TYPE
        SYNTAX  FileSystemCleanIndexTC 
        MAX-ACCESS  not-accessible
        STATUS  current
        DESCRIPTION
            "fileSystem Clean index"
        ::= { fileSystemCleanEntry 1 }

    fileSystemCleanStatus OBJECT-TYPE
        SYNTAX  FileSystemCleanStatusTC 
        MAX-ACCESS  read-only 
        STATUS  current
        DESCRIPTION
            "fileSystem Clean Status"
        ::= { fileSystemCleanEntry 2 }

    fileSystemCleanSchedule OBJECT-TYPE
        SYNTAX  FileSystemCleanScheduleTC 
        MAX-ACCESS  read-only 
        STATUS  current
        DESCRIPTION
            "fileSystem Clean Schedule"
        ::= { fileSystemCleanEntry 3 }

    fileSystemCleanThrottle OBJECT-TYPE
        SYNTAX  FileSystemCleanThrottleTC 
        MAX-ACCESS  read-only 
        STATUS  current
        DESCRIPTION
            "fileSystem Clean Throttle"
        ::= { fileSystemCleanEntry 4 }

-- **********************************************************************
--
-- fileSystemOptions
-- ====================
--
-- dataDomainMib                (1.3.6.1.4.1.19746)
--   dataDomainMibObjects       (1.3.6.1.4.1.19746.1)
--     fileSystem                     (1.3.6.1.4.1.19746.1.3)
--       fileSystemOptions              (1.3.6.1.4.1.19746.1.3.4)
--
-- **********************************************************************

    fileSystemOptions		    OBJECT IDENTIFIER ::= { fileSystem 4 }

    fileSystemOptionsTable OBJECT-TYPE
        SYNTAX  SEQUENCE OF FileSystemOptionsEntry
        MAX-ACCESS  not-accessible
        STATUS  current
        DESCRIPTION
            "A table containing entries of fileSystemOptionsEntry."
        ::= { fileSystemOptions 1 }

    fileSystemOptionsEntry OBJECT-TYPE
        SYNTAX  FileSystemOptionsEntry
        MAX-ACCESS  not-accessible
        STATUS  current
        DESCRIPTION
        "fileSystemOptionsTable Row Description"
        INDEX { fileSystemOptionsIndex }
        ::= { fileSystemOptionsTable 1 }

    FileSystemOptionsEntry ::= SEQUENCE {
        fileSystemOptionsIndex          FileSystemOptionsIndexTC,
        fileSystemOptionsName           FileSystemOptionsNameTC,
        fileSystemOptionsValue          FileSystemOptionsValueTC
    }

    fileSystemOptionsIndex OBJECT-TYPE
        SYNTAX  FileSystemOptionsIndexTC 
        MAX-ACCESS  not-accessible
        STATUS  current
        DESCRIPTION
            "fileSystem Options index"
        ::= { fileSystemOptionsEntry 1 }

    fileSystemOptionsName OBJECT-TYPE
        SYNTAX  FileSystemOptionsNameTC 
        MAX-ACCESS  read-only 
        STATUS  current
        DESCRIPTION
            "fileSystem Options name"
        ::= { fileSystemOptionsEntry 2 }

    fileSystemOptionsValue OBJECT-TYPE
        SYNTAX  FileSystemOptionsValueTC 
        MAX-ACCESS  read-only 
        STATUS  current
        DESCRIPTION
            "fileSystem Options Value"
        ::= { fileSystemOptionsEntry 3 }


-- **********************************************************************
--
-- fileSystemArchiveUnit
-- ====================
--
-- dataDomainMib                (1.3.6.1.4.1.19746)
--   dataDomainMibObjects       (1.3.6.1.4.1.19746.1)
--     fileSystem                     (1.3.6.1.4.1.19746.1.3)
--       fileSystemArchiveUnit           (1.3.6.1.4.1.19746.1.3.6)
--
-- **********************************************************************

    fileSystemArchiveUnit		    OBJECT IDENTIFIER ::= { fileSystem 6 }

    fileSystemArchiveUnitTable OBJECT-TYPE
        SYNTAX  SEQUENCE OF FileSystemArchiveUnitEntry
        MAX-ACCESS  not-accessible
        STATUS  current
        DESCRIPTION
            "A table containing entries of fileSystemArchiveUnitEntry."
        ::= { fileSystemArchiveUnit 1 }

    fileSystemArchiveUnitEntry OBJECT-TYPE
        SYNTAX  FileSystemArchiveUnitEntry
        MAX-ACCESS  not-accessible
        STATUS  current
        DESCRIPTION
        "fileSystemArchiveUnitTable Row Description"
        INDEX { fileSystemArchiveUnitIndex }
        ::= { fileSystemArchiveUnitTable 1 }

    FileSystemArchiveUnitEntry ::= SEQUENCE {
        fileSystemArchiveUnitIndex             DDMibTableIndexTC,
        fileSystemArchiveUnitName              DDMibTableString256TC,
        fileSystemArchiveUnitState             FileSystemArchiveUnitStateTC,
        fileSystemArchiveUnitStatus            FileSystemArchiveUnitStatusTC,
        fileSystemArchiveUnitStartTime         DDMibTimeStampTC,
        fileSystemArchiveUnitEndTime           DDMibTimeStampTC,
        fileSystemArchiveUnitSize              DDMibTableSizeGibTC,
        fileSystemArchiveUnitDiskGroups        DDMibTableString1024TC
    }

    fileSystemArchiveUnitIndex OBJECT-TYPE
        SYNTAX  DDMibTableIndexTC 
        MAX-ACCESS  not-accessible
        STATUS  current
        DESCRIPTION
            "fileSystem ArchiveUnit index"
        ::= { fileSystemArchiveUnitEntry 1 }

    fileSystemArchiveUnitName OBJECT-TYPE
        SYNTAX  DDMibTableString256TC 
        MAX-ACCESS  read-only 
        STATUS  current
        DESCRIPTION
            "fileSystem ArchiveUnit Name"
        ::= { fileSystemArchiveUnitEntry 2 }

    fileSystemArchiveUnitState OBJECT-TYPE
        SYNTAX FileSystemArchiveUnitStateTC 
        MAX-ACCESS  read-only 
        STATUS  current
        DESCRIPTION
            "fileSystem ArchiveUnit State"
        ::= { fileSystemArchiveUnitEntry 3 }

    fileSystemArchiveUnitStatus OBJECT-TYPE
        SYNTAX  FileSystemArchiveUnitStatusTC
        MAX-ACCESS  read-only 
        STATUS  current
        DESCRIPTION
            "fileSystem ArchiveUnit Status"
        ::= { fileSystemArchiveUnitEntry 4 }

    fileSystemArchiveUnitStartTime OBJECT-TYPE
        SYNTAX  DDMibTimeStampTC 
        MAX-ACCESS read-only 
        STATUS  current
        DESCRIPTION
            "fileSystem ArchiveUnit start Time"
        ::= { fileSystemArchiveUnitEntry 5 }

    fileSystemArchiveUnitEndTime OBJECT-TYPE
        SYNTAX  DDMibTimeStampTC 
        MAX-ACCESS  read-only 
        STATUS  current
        DESCRIPTION
            "fileSystem ArchiveUnit End Time"
        ::= { fileSystemArchiveUnitEntry 6 }

    fileSystemArchiveUnitSize OBJECT-TYPE
        SYNTAX  DDMibTableSizeGibTC 
        MAX-ACCESS  read-only 
        STATUS  current
        DESCRIPTION
            "fileSystem ArchiveUnit Size in Gib"
        ::= { fileSystemArchiveUnitEntry 7 }

    fileSystemArchiveUnitDiskGroups OBJECT-TYPE
        SYNTAX  DDMibTableString1024TC 
        MAX-ACCESS  read-only 
        STATUS  current
        DESCRIPTION
            "fileSystem ArchiveUnit DiskGroups"
        ::= { fileSystemArchiveUnitEntry 8 }

-- **********************************************************************
--
-- CurrentAlerts 
-- =============
--
-- dataDomainMib        		(1.3.6.1.4.1.19746)
--   dataDomainMibObjects		(1.3.6.1.4.1.19746.1)
--	alerts				(1.3.6.1.4.1.19746.1.4)
--	    currentAlerts		(1.3.6.1.4.1.19746.1.4.1)
--
-- **********************************************************************

    currentAlerts	    OBJECT IDENTIFIER ::= { alerts 1 }

    currentAlertTable OBJECT-TYPE
        SYNTAX  SEQUENCE OF CurrentAlertEntry
        MAX-ACCESS  not-accessible
        STATUS  current
        DESCRIPTION
            "A table containing entries of CurrentAlertEntry."
        ::= { currentAlerts 1 }

    currentAlertEntry OBJECT-TYPE
        SYNTAX  CurrentAlertEntry
        MAX-ACCESS  not-accessible
        STATUS  current
        DESCRIPTION 
	    "currentAlertTable Row Description" 
        INDEX { currentAlertIndex }
        ::= { currentAlertTable 1 }

    CurrentAlertEntry ::= SEQUENCE {
	currentAlertIndex	AlertIndexTC,
	currentAlertTimestamp	AlertTimestampTC,
	currentAlertDescription	AlertDescriptionTC
    }

    currentAlertIndex OBJECT-TYPE
        SYNTAX  AlertIndexTC 
        MAX-ACCESS  not-accessible
        STATUS  current
        DESCRIPTION
            "Current Alert Row index"
        ::= { currentAlertEntry 1 }

    currentAlertTimestamp OBJECT-TYPE
        SYNTAX  AlertTimestampTC 
        MAX-ACCESS  read-only
        STATUS  current
        DESCRIPTION
            "Timestamp of current alert"
        ::= { currentAlertEntry 2 }

    currentAlertDescription OBJECT-TYPE
        SYNTAX  AlertDescriptionTC 
        MAX-ACCESS  read-only
        STATUS  current
        DESCRIPTION
            "Alert Description"
        ::= { currentAlertEntry 3 }

-- **********************************************************************
--
-- SystemStats 
-- ===========
--
-- dataDomainMib        		(1.3.6.1.4.1.19746)
--   dataDomainMibObjects		(1.3.6.1.4.1.19746.1)
--	statistics			(1.3.6.1.4.1.19746.1.5)
--	    systemStats			(1.3.6.1.4.1.19746.1.5.1)
--
-- **********************************************************************

    systemStats		    OBJECT IDENTIFIER ::= { statistics 1 }

    systemStatsTable OBJECT-TYPE
        SYNTAX  SEQUENCE OF SystemStatsEntry
        MAX-ACCESS  not-accessible
        STATUS  current
        DESCRIPTION
            "A table containing entries of SystemStatsEntry."
        ::= { systemStats 1 }

    systemStatsEntry OBJECT-TYPE
        SYNTAX  SystemStatsEntry
        MAX-ACCESS  not-accessible
        STATUS  current
        DESCRIPTION 
	    "systemStatsTable Row Description" 
        INDEX { systemStatsIndex }
        ::= { systemStatsTable 1 }

    SystemStatsEntry ::= SEQUENCE {
	systemStatsIndex	    SystemStatsIndexTC,
	cpuAvgPercentageBusy	    Percentage,
	cpuMaxPercentageBusy	    Percentage,
	nfsOpsPerSecond		    OpsPerSecond,
	nfsIdlePercentage	    Percentage,
	nfsProcPercentage	    Percentage,
	nfsSendPercentage	    Percentage,
	nfsReceivePercentage	    Percentage,
	cifsOpsPerSecond	    OpsPerSecond,
	diskReadKBytesPerSecond	    KBytesPerSecond,
	diskWriteKBytesPerSecond    KBytesPerSecond,
	diskBusyPercentage	    Percentage,
	nvramReadKBytesPerSecond    KBytesPerSecond,
	nvramWriteKBytesPerSecond   KBytesPerSecond,
	replInKBytesPerSecond	    KBytesPerSecond,
	replOutKBytesPerSecond	    KBytesPerSecond 
    }

    systemStatsIndex OBJECT-TYPE
        SYNTAX  SystemStatsIndexTC 
        MAX-ACCESS  not-accessible
        STATUS  current
        DESCRIPTION
            "System Stats Row index"
        ::= { systemStatsEntry 1 }

    cpuAvgPercentageBusy OBJECT-TYPE
        SYNTAX  Percentage 
        MAX-ACCESS  read-only
        STATUS  current
        DESCRIPTION
            "CPU Average Percentage Busy"
        ::= { systemStatsEntry 2 }

    cpuMaxPercentageBusy OBJECT-TYPE
        SYNTAX  Percentage 
        MAX-ACCESS  read-only
        STATUS  current
        DESCRIPTION
            "CPU Max Percentage Busy"
        ::= { systemStatsEntry 3 }

    nfsOpsPerSecond OBJECT-TYPE
        SYNTAX  OpsPerSecond 
        MAX-ACCESS  read-only
        STATUS  current
        DESCRIPTION
            "Number of NFS Operations performed per second"
        ::= { systemStatsEntry 4 }

    nfsIdlePercentage OBJECT-TYPE
        SYNTAX  Percentage 
        MAX-ACCESS  read-only
        STATUS  current
        DESCRIPTION
            "Percentage of time NFS was Idle"
        ::= { systemStatsEntry 5 }

    nfsProcPercentage OBJECT-TYPE
        SYNTAX  Percentage 
        MAX-ACCESS  read-only
        STATUS  current
        DESCRIPTION
            "Percentage of time NFS was processing"
        ::= { systemStatsEntry 6 }

    nfsSendPercentage OBJECT-TYPE
        SYNTAX  Percentage 
        MAX-ACCESS  read-only
        STATUS  current
        DESCRIPTION
            "Percentage of time NFS was sending requests"
        ::= { systemStatsEntry 7 }

    nfsReceivePercentage OBJECT-TYPE
        SYNTAX  Percentage 
        MAX-ACCESS  read-only
        STATUS  current
        DESCRIPTION
            "Percentage of time NFS was receiving requests"
        ::= { systemStatsEntry 8 }

    cifsOpsPerSecond OBJECT-TYPE
        SYNTAX  OpsPerSecond 
        MAX-ACCESS  read-only
        STATUS  current
        DESCRIPTION
            "Number of CIFS Operations performed per second"
        ::= { systemStatsEntry 9 }

    diskReadKBytesPerSecond OBJECT-TYPE
        SYNTAX  KBytesPerSecond 
        MAX-ACCESS  read-only
        STATUS  current
        DESCRIPTION
            "Number of KBytes per second read from disk"
        ::= { systemStatsEntry 10 }

    diskWriteKBytesPerSecond OBJECT-TYPE
        SYNTAX  KBytesPerSecond 
        MAX-ACCESS  read-only
        STATUS  current
        DESCRIPTION
            "Number of KBytes per second written on disk"
        ::= { systemStatsEntry 11 }

    diskBusyPercentage OBJECT-TYPE
        SYNTAX  Percentage 
        MAX-ACCESS  read-only
        STATUS  current
        DESCRIPTION
            "Percentage of Time Disks were busy"
        ::= { systemStatsEntry 12 }

    nvramReadKBytesPerSecond OBJECT-TYPE
        SYNTAX  KBytesPerSecond 
        MAX-ACCESS  read-only
        STATUS  current
        DESCRIPTION
            "Number of KBytes read per second from NVRAM"
        ::= { systemStatsEntry 13 }

    nvramWriteKBytesPerSecond OBJECT-TYPE
        SYNTAX  KBytesPerSecond 
        MAX-ACCESS  read-only
        STATUS  current
        DESCRIPTION
            "Number of KBytes written per second on NVRAM"
        ::= { systemStatsEntry 14 }

    replInKBytesPerSecond OBJECT-TYPE
        SYNTAX  KBytesPerSecond 
        MAX-ACCESS  read-only
        STATUS  current
        DESCRIPTION
            "Number of KBytes per second received for Replication"
        ::= { systemStatsEntry 15 }

    replOutKBytesPerSecond OBJECT-TYPE
        SYNTAX  KBytesPerSecond 
        MAX-ACCESS  read-only
        STATUS  current
        DESCRIPTION
            "Number of KBytes per second sent for Replication"
        ::= { systemStatsEntry 16 }

-- **********************************************************************
--
-- DiskProperties
-- ==============
--
-- dataDomainMib        		(1.3.6.1.4.1.19746)
--   dataDomainMibObjects		(1.3.6.1.4.1.19746.1)
--	diskStorage			(1.3.6.1.4.1.19746.1.6)
--	    diskProperties		(1.3.6.1.4.1.19746.1.6.1)
--
-- **********************************************************************

    diskProperties	    OBJECT IDENTIFIER ::= { diskStorage 1 }

    diskPropertiesTable OBJECT-TYPE
        SYNTAX  SEQUENCE OF DiskPropertiesEntry
        MAX-ACCESS  not-accessible
        STATUS  current
        DESCRIPTION
            "A table containing entries of DiskPropertiesEntry."
        ::= { diskProperties 1 }

    diskPropertiesEntry OBJECT-TYPE
        SYNTAX  DiskPropertiesEntry
        MAX-ACCESS  not-accessible
        STATUS  current
        DESCRIPTION "diskPropertiesTable Row Description" 
        INDEX { diskPropEnclosureID, diskPropIndex }
        ::= { diskPropertiesTable 1 }

    DiskPropertiesEntry ::= SEQUENCE {
    diskPropEnclosureID		EnclosureID,
	diskPropIndex	    DiskIndexTC,
        diskPropTrapIndex   DiskIndexTC,
	diskModel	    DiskModelTC,
	diskFirmwareVersion DiskFirmwareVersionTC,
	diskSerialNumber    DiskSerialNumberTC,
	diskCapacity	    DiskCapacityTC,
	diskPropState	    DiskStateTC
    }

    diskPropEnclosureID OBJECT-TYPE
        SYNTAX  EnclosureID
        MAX-ACCESS  not-accessible
        STATUS  current
        DESCRIPTION
            "Enclosure ID of disk"
        ::= { diskPropertiesEntry 1 }

    diskPropIndex OBJECT-TYPE
        SYNTAX  DiskIndexTC
        MAX-ACCESS  not-accessible
        STATUS  current
        DESCRIPTION
            "Disk Number"
        ::= { diskPropertiesEntry 2 }

    diskPropTrapIndex OBJECT-TYPE
        SYNTAX  DiskIndexTC
        MAX-ACCESS  read-only
        STATUS  current
        DESCRIPTION
            "Disk Number for Traps"
        ::= { diskPropertiesEntry 3 }

    diskModel OBJECT-TYPE
        SYNTAX	DiskModelTC 
        MAX-ACCESS  read-only
        STATUS  current
        DESCRIPTION 
	    "Manufacture and model of the disk"
        ::= { diskPropertiesEntry 4 }

    diskFirmwareVersion OBJECT-TYPE
        SYNTAX	DiskFirmwareVersionTC
        MAX-ACCESS  read-only
        STATUS  current
        DESCRIPTION 
	    "Firmware version of the disk"
        ::= { diskPropertiesEntry 5 }

    diskSerialNumber OBJECT-TYPE
        SYNTAX	DiskSerialNumberTC
        MAX-ACCESS  read-only
        STATUS  current
        DESCRIPTION 
	    "Serial Number of the disk"
        ::= { diskPropertiesEntry 6 }

    diskCapacity OBJECT-TYPE
        SYNTAX	DiskCapacityTC
        MAX-ACCESS  read-only
        STATUS  current
        DESCRIPTION 
	    "Capacity of the disk"
        ::= { diskPropertiesEntry 7 }

    diskPropState OBJECT-TYPE
        SYNTAX	DiskStateTC
        MAX-ACCESS  read-only
        STATUS  current
        DESCRIPTION 
	    "Current State of the disk"
        ::= { diskPropertiesEntry 8 }

-- **********************************************************************
--
-- DiskPerformance
-- ===============
--
-- dataDomainMib        		(1.3.6.1.4.1.19746)
--   dataDomainMibObjects		(1.3.6.1.4.1.19746.1)
--	diskStorage			(1.3.6.1.4.1.19746.1.6)
--	    diskPerformance		(1.3.6.1.4.1.19746.1.6.2)
--
-- **********************************************************************

    diskPerformance	    OBJECT IDENTIFIER ::= { diskStorage 2 }

    diskPerformanceTable OBJECT-TYPE
        SYNTAX  SEQUENCE OF DiskPerformanceEntry
        MAX-ACCESS  not-accessible
        STATUS  current
        DESCRIPTION
            "A table containing entries of DiskPerformanceEntry."
        ::= { diskPerformance 1 }

    diskPerformanceEntry OBJECT-TYPE
        SYNTAX  DiskPerformanceEntry
        MAX-ACCESS  not-accessible
        STATUS  current
        DESCRIPTION 
	    "diskPerformanceTable Row Description" 
        INDEX { diskPerfEnclosureID, diskPerfIndex }
        ::= { diskPerformanceTable 1 }

    DiskPerformanceEntry ::= SEQUENCE {
    diskPerfEnclosureID		EnclosureID,
	diskPerfIndex	    DiskIndexTC,
	diskSectorsRead	    DiskSectorsPerSecondTC,
	diskSectorsWritten  DiskSectorsPerSecondTC,
	diskTotalKBytes	    KBytesPerSecond,
	diskBusy	    Percentage,
        diskPerfState	    DiskStateTC
    }

    diskPerfEnclosureID OBJECT-TYPE
        SYNTAX  EnclosureID
        MAX-ACCESS  not-accessible
        STATUS  current
        DESCRIPTION
            "Enclosure ID of disk"
        ::= { diskPerformanceEntry 1 }

    diskPerfIndex OBJECT-TYPE
        SYNTAX  DiskIndexTC
        MAX-ACCESS  not-accessible
        STATUS  current
        DESCRIPTION
            "Disk Number"
        ::= { diskPerformanceEntry 2 }

    diskSectorsRead OBJECT-TYPE
        SYNTAX  DiskSectorsPerSecondTC
        MAX-ACCESS  read-only
        STATUS  current
        DESCRIPTION
            "Number of disk sectors read per second"
        ::= { diskPerformanceEntry 3 }

    diskSectorsWritten OBJECT-TYPE
        SYNTAX  DiskSectorsPerSecondTC
        MAX-ACCESS  read-only
        STATUS  current
        DESCRIPTION
            "Number of disk sectors written per second"
        ::= { diskPerformanceEntry 4 }

    diskTotalKBytes OBJECT-TYPE
        SYNTAX  KBytesPerSecond
        MAX-ACCESS  read-only
        STATUS  current
        DESCRIPTION
            "Total Number of Kilo-bytes read/written per second"
        ::= { diskPerformanceEntry 5 }

    diskBusy OBJECT-TYPE
        SYNTAX  Percentage
        MAX-ACCESS  read-only
        STATUS  current
        DESCRIPTION
            "Percentage of time disk is busy"
        ::= { diskPerformanceEntry 6 }

    diskPerfState OBJECT-TYPE
        SYNTAX  DiskStateTC
        MAX-ACCESS  read-only
        STATUS  current
        DESCRIPTION
            "Current State of the disk"
        ::= { diskPerformanceEntry 7 }

-- **********************************************************************
--
-- DiskReliability
-- ===============
--
-- dataDomainMib        		(1.3.6.1.4.1.19746)
--   dataDomainMibObjects		(1.3.6.1.4.1.19746.1)
--	diskStorage			(1.3.6.1.4.1.19746.1.6)
--	    diskReliability		(1.3.6.1.4.1.19746.1.6.3)
--
-- **********************************************************************

    diskReliability	    OBJECT IDENTIFIER ::= { diskStorage 3 }

    diskReliabilityTable OBJECT-TYPE
        SYNTAX  SEQUENCE OF DiskReliabilityEntry
        MAX-ACCESS  not-accessible
        STATUS  current
        DESCRIPTION
            "A table containing entries of DiskReliabilityEntry."
        ::= { diskReliability 1 }

    diskReliabilityEntry OBJECT-TYPE
        SYNTAX  DiskReliabilityEntry
        MAX-ACCESS  not-accessible
        STATUS  current
        DESCRIPTION 
	    "diskReliabilityTable Row Description" 
        INDEX { diskErrEnclosureID, diskErrIndex }
        ::= { diskReliabilityTable 1 }

    DiskReliabilityEntry ::= SEQUENCE {
    diskErrEnclosureID	EnclosureID,
	diskErrIndex		DiskIndexTC,
        diskErrTrapIndex        DiskIndexTC,
	diskTemperature		Temperature,
	diskTimeoutCount	ErrorCount,
	diskReadFailCount	ErrorCount,
	diskWriteFailCount	ErrorCount,
	diskMiscFailCount	ErrorCount,
	diskOffTrackErrCount	ErrorCount,
	diskSoftEccCount	ErrorCount,
	diskCrcErrCount		ErrorCount,
	diskProbationalCount	ErrorCount,
	diskReallocCount	ErrorCount,
	diskErrState		DiskStateTC 
    }

    diskErrEnclosureID OBJECT-TYPE
        SYNTAX  EnclosureID
        MAX-ACCESS  not-accessible
        STATUS  current
        DESCRIPTION
            "Enclosure ID of disk"
        ::= { diskReliabilityEntry 1 }

    diskErrIndex OBJECT-TYPE
        SYNTAX  DiskIndexTC
        MAX-ACCESS  not-accessible
        STATUS  current
        DESCRIPTION
            "Disk Number"
        ::= { diskReliabilityEntry 2 }

    diskErrTrapIndex OBJECT-TYPE
        SYNTAX  DiskIndexTC
        MAX-ACCESS read-only 
        STATUS  current
        DESCRIPTION
            "Disk Number for Traps"
        ::= { diskReliabilityEntry 3 }

    diskTemperature OBJECT-TYPE
        SYNTAX  Temperature 
        MAX-ACCESS  read-only
        STATUS  current
        DESCRIPTION
            "Current Disk Temperature in Celsius"
        ::= { diskReliabilityEntry 4 }

    diskTimeoutCount OBJECT-TYPE
        SYNTAX  ErrorCount 
        MAX-ACCESS  read-only
        STATUS  current
        DESCRIPTION
            "Number of command timeouts"
        ::= { diskReliabilityEntry 5 }

    diskReadFailCount OBJECT-TYPE
        SYNTAX  ErrorCount 
        MAX-ACCESS  read-only
        STATUS  current
        DESCRIPTION
            "Number of read failures"
        ::= { diskReliabilityEntry 6 }

    diskWriteFailCount OBJECT-TYPE
        SYNTAX  ErrorCount 
        MAX-ACCESS  read-only
        STATUS  current
        DESCRIPTION
            "Number of write failures"
        ::= { diskReliabilityEntry 7 }

    diskMiscFailCount OBJECT-TYPE
        SYNTAX  ErrorCount 
        MAX-ACCESS  read-only
        STATUS  current
        DESCRIPTION
            "Number of miscellaneous failures"
        ::= { diskReliabilityEntry 8 }

    diskOffTrackErrCount OBJECT-TYPE
        SYNTAX  ErrorCount 
        MAX-ACCESS  read-only
        STATUS  current
        DESCRIPTION
            "Number of offtrack errors"
        ::= { diskReliabilityEntry 9 }

    diskSoftEccCount OBJECT-TYPE
        SYNTAX  ErrorCount 
        MAX-ACCESS  read-only
        STATUS  current
        DESCRIPTION
            "Number of soft ecc errors"
        ::= { diskReliabilityEntry 10 }

    diskCrcErrCount OBJECT-TYPE
        SYNTAX  ErrorCount 
        MAX-ACCESS  read-only
        STATUS  current
        DESCRIPTION
            "Number of crc errors"
        ::= { diskReliabilityEntry 11 }

    diskProbationalCount OBJECT-TYPE
        SYNTAX  ErrorCount 
        MAX-ACCESS  read-only
        STATUS  current
        DESCRIPTION
            "Number of probational errors"
        ::= { diskReliabilityEntry 12 }

    diskReallocCount OBJECT-TYPE
        SYNTAX  ErrorCount 
        MAX-ACCESS  read-only
        STATUS  current
        DESCRIPTION
            "Number of reallocation errors"
        ::= { diskReliabilityEntry 13 }

    diskErrState OBJECT-TYPE
        SYNTAX  DiskStateTC
        MAX-ACCESS  read-only
        STATUS  current
        DESCRIPTION
            "Current State of the disk"
        ::= { diskReliabilityEntry 14 }

-- **********************************************************************
--
-- ReplicationInfo 
-- ========
--
-- dataDomainMib        		(1.3.6.1.4.1.19746)
--   dataDomainMibObjects		(1.3.6.1.4.1.19746.1)
--	replication				(1.3.6.1.4.1.19746.1.8)
--	    replicationInfo			(1.3.6.1.4.1.19746.1.8.1)
--
-- Physical replication is represented with a replContext of 0
-- and has its bytes sent and received put in replPostCompBytesSent
-- and replPostCompBytesReceived respectively
-- **********************************************************************

    replicationInfo		    OBJECT IDENTIFIER ::= { replication 1 }

    replicationInfoTable OBJECT-TYPE
        SYNTAX  SEQUENCE OF ReplicationInfoEntry
        MAX-ACCESS  not-accessible
        STATUS  current
        DESCRIPTION
            "A table containing entries of ReplicationInfoEntry."
        ::= { replicationInfo 1 }

    replicationInfoEntry OBJECT-TYPE
        SYNTAX  ReplicationInfoEntry
        MAX-ACCESS  not-accessible
        STATUS  current
        DESCRIPTION 
	    "replicationInfoTable Row Description" 
        INDEX { replContext }
        ::= { replicationInfoTable 1 }

    ReplicationInfoEntry ::= SEQUENCE {
	replContext		     		ReplicationContextTC,
        replTrapContext		     		ReplicationContextTC,
	replState			  	  	ReplicationStateTC,
	replStatus			  		ReplicationStatusTC,
	replFileSysStatus			FileSystemStatusTC,
	replConnTime		    	ReplicationConnectTimeTC,
	replSource			    	ReplicationPathTC, 
	replDestination 			ReplicationPathTC,
	replPreCompBytesSent	    ReplicationTrafficTC,
	replPostCompBytesSent       ReplicationTrafficTC,
	replPreCompBytesRemaining   ReplicationTrafficTC,
	replPostCompBytesReceived   ReplicationTrafficTC,
	replThrottle				ReplicationThrottleTC,
	replSyncedAsOfTime			ReplicationSyncedTimeTC
    }

    replContext OBJECT-TYPE
        SYNTAX  ReplicationContextTC
        MAX-ACCESS  not-accessible
        STATUS  current
        DESCRIPTION
            "context ID of replication source/dest pair"
        ::= { replicationInfoEntry 1 }

    replTrapContext OBJECT-TYPE
        SYNTAX  ReplicationContextTC
        MAX-ACCESS  read-only
        STATUS  current
        DESCRIPTION
            "context ID of replication source/dest pair for traps"
        ::= { replicationInfoEntry 2 }
        
    replState OBJECT-TYPE
        SYNTAX  ReplicationStateTC
        MAX-ACCESS  read-only
        STATUS  current
        DESCRIPTION
            "state of replication source/dest pair"
        ::= { replicationInfoEntry 3 }

    replStatus OBJECT-TYPE
        SYNTAX  ReplicationStatusTC
        MAX-ACCESS  read-only
        STATUS  current
        DESCRIPTION
            "status of replication source/dest pair connection"
        ::= { replicationInfoEntry 4 }

    replFileSysStatus OBJECT-TYPE
        SYNTAX  FileSystemStatusTC
        MAX-ACCESS  read-only
        STATUS  current
        DESCRIPTION
            "status of filesystem"
        ::= { replicationInfoEntry 5 }

    replConnTime OBJECT-TYPE
        SYNTAX  ReplicationConnectTimeTC
        MAX-ACCESS  read-only
        STATUS  current
        DESCRIPTION
            "time of connection established between source and dest,
             or time since disconnect if status is 'disconnected'"
        ::= { replicationInfoEntry 6 }

    replSource OBJECT-TYPE
        SYNTAX  ReplicationPathTC
        MAX-ACCESS  read-only
        STATUS  current
        DESCRIPTION
            "network path to replication source directory"
        ::= { replicationInfoEntry 7 }

    replDestination OBJECT-TYPE
        SYNTAX  ReplicationPathTC
        MAX-ACCESS  read-only
        STATUS  current
        DESCRIPTION
            "network path to replication destination directory"
        ::= { replicationInfoEntry 8 }

    replPreCompBytesSent OBJECT-TYPE
        SYNTAX  ReplicationTrafficTC
        MAX-ACCESS  read-only
        STATUS  current
        DESCRIPTION
            "pre compression bytes sent"
        ::= { replicationInfoEntry 9 }

    replPostCompBytesSent OBJECT-TYPE
        SYNTAX  ReplicationTrafficTC
        MAX-ACCESS  read-only
        STATUS  current
        DESCRIPTION
            "post compression bytes sent"
        ::= { replicationInfoEntry 10 }

    replPreCompBytesRemaining OBJECT-TYPE
        SYNTAX  ReplicationTrafficTC
        MAX-ACCESS  read-only
        STATUS  current
        DESCRIPTION
            "pre compression bytes remaining"
        ::= { replicationInfoEntry 11 }

    replPostCompBytesReceived OBJECT-TYPE
        SYNTAX  ReplicationTrafficTC
        MAX-ACCESS  read-only
        STATUS  current
        DESCRIPTION
            "post compression bytes received"
        ::= { replicationInfoEntry 12 }

    replThrottle OBJECT-TYPE
        SYNTAX  ReplicationThrottleTC
        MAX-ACCESS  read-only
        STATUS  current
        DESCRIPTION
            "replication throttle in bps -- -1 is disabled, 0 unlimited"
        ::= { replicationInfoEntry 13 }

    replSyncedAsOfTime OBJECT-TYPE
        SYNTAX  ReplicationSyncedTimeTC
        MAX-ACCESS  read-only
        STATUS  current
        DESCRIPTION
            "time when the source and destination were in sync,
             or 0 if the time is unknown"
        ::= { replicationInfoEntry 14 }

-- **********************************************************************
--
-- ReplicationConfig 
-- ========
--
-- dataDomainMib        		(1.3.6.1.4.1.19746)
--   dataDomainMibObjects		(1.3.6.1.4.1.19746.1)
--	replication				(1.3.6.1.4.1.19746.1.8)
--	    replicationConfig			(1.3.6.1.4.1.19746.1.8.2)
--
-- **********************************************************************

    replicationConfig		    OBJECT IDENTIFIER ::= { replication 2 }

    replicationConfigTable OBJECT-TYPE
        SYNTAX  SEQUENCE OF ReplicationConfigEntry
        MAX-ACCESS  not-accessible
        STATUS  current
        DESCRIPTION
            "A table containing entries of ReplicationConfigEntry."
        ::= { replicationConfig 1 }

    replicationConfigEntry OBJECT-TYPE
        SYNTAX  ReplicationConfigEntry
        MAX-ACCESS  not-accessible
        STATUS  current
        DESCRIPTION 
	    "replicationConfigTable Row Description" 
        INDEX { replConfigIndex }
        ::= { replicationConfigTable 1 }

    ReplicationConfigEntry ::= SEQUENCE {
	replConfigIndex		     		ReplicationConfigIndexTC,
	replConfigContextId	  	  	ReplicationConfigContextIdTC,
	replConfigSource			ReplicationConfigSourceTC,
	replConfigDest			        ReplicationConfigDestTC,
	replConfigConnHost		    	ReplicationConfigConnHostTC,
	replConfigConnPort		    	ReplicationConfigConnPortTC, 
	replConfigLowBWOptim 			ReplicationConfigLowBWOptimTC,
	replConfigEnabled			ReplicationConfigEnabledTC
    }

    replConfigIndex OBJECT-TYPE
        SYNTAX  ReplicationConfigIndexTC
        MAX-ACCESS  not-accessible
        STATUS  current
        DESCRIPTION
            "ConfigIndex ID of replication source/dest pair"
        ::= { replicationConfigEntry 1 }

    replConfigContextId OBJECT-TYPE
        SYNTAX  ReplicationConfigContextIdTC
        MAX-ACCESS  read-only
        STATUS  current
        DESCRIPTION
            "ConfigContextId of replication source/dest pair"
        ::= { replicationConfigEntry 2 }

    replConfigSource OBJECT-TYPE
        SYNTAX  ReplicationConfigSourceTC
        MAX-ACCESS  read-only
        STATUS  current
        DESCRIPTION
            "Source for replication source/dest pair connection"
        ::= { replicationConfigEntry 3 }

    replConfigDest OBJECT-TYPE
        SYNTAX  ReplicationConfigDestTC
        MAX-ACCESS  read-only
        STATUS  current
        DESCRIPTION
            "Destination for replication connection"
        ::= { replicationConfigEntry 4 }

    replConfigConnHost OBJECT-TYPE
        SYNTAX  ReplicationConfigConnHostTC
        MAX-ACCESS  read-only
        STATUS  current
        DESCRIPTION
            "Host for a replication connection"
        ::= { replicationConfigEntry 5 }

    replConfigConnPort OBJECT-TYPE
        SYNTAX  ReplicationConfigConnPortTC
        MAX-ACCESS  read-only
        STATUS  current
        DESCRIPTION
            "Replication Configuration port for the connection"
        ::= { replicationConfigEntry 6 }

    replConfigLowBWOptim OBJECT-TYPE
        SYNTAX  ReplicationConfigLowBWOptimTC
        MAX-ACCESS  read-only
        STATUS  current
        DESCRIPTION
            "Replication configuration Low BW optim"
        ::= { replicationConfigEntry 7 }

    replConfigEnabled OBJECT-TYPE
        SYNTAX  ReplicationConfigEnabledTC
        MAX-ACCESS  read-only
        STATUS  current
        DESCRIPTION
            "Replication config Enabled"
        ::= { replicationConfigEntry 8 }


-- **********************************************************************
--
-- nfsProperties 
-- ====================
--
-- dataDomainMib                (1.3.6.1.4.1.19746)
--   dataDomainMibObjects       (1.3.6.1.4.1.19746.1)
--     nfs                      (1.3.6.1.4.1.19746.1.9)
--      nfsProperties           (1.3.6.1.4.1.19746.1.9.1)
--
-- **********************************************************************

    nfsProperties		    OBJECT IDENTIFIER ::= { nfs 1 }

    nfsStatus OBJECT-TYPE
        SYNTAX  NfsStatusTC
        MAX-ACCESS  read-only
        STATUS  current
        DESCRIPTION "Status of the network file system"
        ::= { nfsProperties 1 }

-- **********************************************************************
--
-- nfsClient
-- ====================
--
-- dataDomainMib                (1.3.6.1.4.1.19746)
--   dataDomainMibObjects       (1.3.6.1.4.1.19746.1)
--     nfs                      (1.3.6.1.4.1.19746.1.9)
--      nfsClient               (1.3.6.1.4.1.19746.1.9.2)
--
-- **********************************************************************

    nfsClient		    OBJECT IDENTIFIER ::= { nfs 2 }

    nfsClientTable OBJECT-TYPE
        SYNTAX  SEQUENCE OF NfsClientEntry
        MAX-ACCESS  not-accessible
        STATUS  current
        DESCRIPTION
            "A table containing entries of NfsClientEntry."
        ::= { nfsClient 1 }

    nfsClientEntry OBJECT-TYPE
        SYNTAX  NfsClientEntry
        MAX-ACCESS  not-accessible
        STATUS  current
        DESCRIPTION
        "nfsClientTable Row Description"
        INDEX { nfsClientIndex }
        ::= { nfsClientTable 1 }

    NfsClientEntry ::= SEQUENCE {
        nfsClientIndex NfsClientIndexTC,
        nfsClientPath  NfsClientPathTC,
        nfsClientClients NfsClientClientsTC,
        nfsClientOptions NfsClientOptionsTC
    }

    nfsClientIndex OBJECT-TYPE
        SYNTAX  NfsClientIndexTC 
        MAX-ACCESS  not-accessible
        STATUS  current
        DESCRIPTION
            "NFS client index"
        ::= { nfsClientEntry 1 }

    nfsClientPath OBJECT-TYPE
        SYNTAX  NfsClientPathTC 
        MAX-ACCESS  read-only 
        STATUS  current
        DESCRIPTION
            "NFS client path"
        ::= { nfsClientEntry 2 }

    nfsClientClients OBJECT-TYPE
        SYNTAX  NfsClientClientsTC 
        MAX-ACCESS  read-only 
        STATUS  current
        DESCRIPTION
            "List of NFS clients"
        ::= { nfsClientEntry 3 }

    nfsClientOptions OBJECT-TYPE
        SYNTAX  NfsClientOptionsTC 
        MAX-ACCESS  read-only 
        STATUS  current
        DESCRIPTION
            "NFS client's options"
        ::= { nfsClientEntry 4 }

-- **********************************************************************
--
-- nfsStats 
-- ====================
--
-- dataDomainMib                (1.3.6.1.4.1.19746)
--   dataDomainMibObjects       (1.3.6.1.4.1.19746.1)
--     nfs                      (1.3.6.1.4.1.19746.1.9)
--      nfsStats                (1.3.6.1.4.1.19746.1.9.3)
--
-- **********************************************************************

    nfsStats		    OBJECT IDENTIFIER ::= { nfs 3 }

    nfsStatsTable OBJECT-TYPE
        SYNTAX  SEQUENCE OF NfsStatsEntry
        MAX-ACCESS  not-accessible
        STATUS  current
        DESCRIPTION
            "A table containing entries of NfsStatsEntry."
        ::= { nfsStats 1 }

    nfsStatsEntry OBJECT-TYPE
        SYNTAX  NfsStatsEntry
        MAX-ACCESS  not-accessible
        STATUS  current
        DESCRIPTION
        "nfsStatsTable Row Description"
        INDEX { nfsStatsIndex }
        ::= { nfsStatsTable 1 }

    NfsStatsEntry ::= SEQUENCE {
        nfsStatsIndex NfsStatsIndexTC,
	    nfsStatsExportPoint NfsStatsExportPointTC,
	    nfsStatsFilesystemType NfsStatsFilesystemTypeTC,
	    nfsStatsCacheEntry NfsStatsCacheEntryTC,
	    nfsStatsFileHandleLookup NfsStatsFileHandleLookupTC,
	    nfsStatsMaxCacheSize NfsStatsMaxCacheSizeTC,
	    nfsStatsCurrentOpenStreams NfsStatsCurrentOpenStreamsTC
    }

    nfsStatsIndex OBJECT-TYPE
        SYNTAX  NfsStatsIndexTC 
        MAX-ACCESS  not-accessible
        STATUS  current
        DESCRIPTION
            "NFS resource index"
        ::= { nfsStatsEntry 1 }

    nfsStatsExportPoint OBJECT-TYPE
        SYNTAX  NfsStatsExportPointTC 
        MAX-ACCESS  read-only
        STATUS  current
        DESCRIPTION
            "NFS export point"
        ::= { nfsStatsEntry 2 }

    nfsStatsFilesystemType OBJECT-TYPE
        SYNTAX  NfsStatsFilesystemTypeTC 
        MAX-ACCESS  read-only
        STATUS  current
        DESCRIPTION
            "File system type"
        ::= { nfsStatsEntry 3 }

    nfsStatsCacheEntry OBJECT-TYPE
        SYNTAX  NfsStatsCacheEntryTC 
        MAX-ACCESS  read-only
        STATUS  current
        DESCRIPTION
            "Number of cache entries"
        ::= { nfsStatsEntry 4 }

    nfsStatsFileHandleLookup OBJECT-TYPE
        SYNTAX  NfsStatsFileHandleLookupTC 
        MAX-ACCESS  read-only
        STATUS  current
        DESCRIPTION
            "File handle lookup count"
        ::= { nfsStatsEntry 5 }

    nfsStatsMaxCacheSize OBJECT-TYPE
        SYNTAX  NfsStatsMaxCacheSizeTC 
        MAX-ACCESS  read-only
        STATUS  current
        DESCRIPTION
            "Max cache size"
        ::= { nfsStatsEntry 6 }

    nfsStatsCurrentOpenStreams OBJECT-TYPE
        SYNTAX  NfsStatsCurrentOpenStreamsTC 
        MAX-ACCESS  read-only
        STATUS  current
        DESCRIPTION
            "Current open stream count"
        ::= { nfsStatsEntry 7 }

-- **********************************************************************
--
-- cifsProperties 
-- ====================
--
-- dataDomainMib                (1.3.6.1.4.1.19746)
--   dataDomainMibObjects       (1.3.6.1.4.1.19746.1)
--     cifs                     (1.3.6.1.4.1.19746.1.10)
--       cifsProperties         (1.3.6.1.4.1.19746.1.10.1)
--         cifsStatus           (1.3.6.1.4.1.19746.1.10.1.1)
--
-- **********************************************************************

    cifsProperties		    OBJECT IDENTIFIER ::= { cifs 1 }

    cifsStatus OBJECT-TYPE
        SYNTAX  CifsStatusTC
        MAX-ACCESS  read-only
        STATUS  current
        DESCRIPTION "CIFS status"
        ::= { cifsProperties 1 }

-- **********************************************************************
--
-- cifsConfig 
-- ====================
--
-- dataDomainMib                       (1.3.6.1.4.1.19746)
--   dataDomainMibObjects              (1.3.6.1.4.1.19746.1)
--     cifs                            (1.3.6.1.4.1.19746.1.10)
--       cifsConfig                    (1.3.6.1.4.1.19746.1.10.2)
--         cifsConfigMode              (1.3.6.1.4.1.19746.1.10.2.1)
--         cifsConfigWINSServer        (1.3.6.1.4.1.19746.1.10.2.2)
--         cifsConfigNetBIOSHostname   (1.3.6.1.4.1.19746.1.10.2.3)
--         cifsConfigDomainController  (1.3.6.1.4.1.19746.1.10.2.4)
--         cifsConfigDNS               (1.3.6.1.4.1.19746.1.10.2.5)
--         cifsConfigGroupname         (1.3.6.1.4.1.19746.1.10.2.6)
--
-- **********************************************************************

    cifsConfig		    OBJECT IDENTIFIER ::= { cifs 2 }

    cifsConfigMode OBJECT-TYPE
        SYNTAX  CifsConfigModeTC
        MAX-ACCESS  read-only
        STATUS  current
        DESCRIPTION "CIFS configuration mode"
        ::= { cifsConfig 1 }

    cifsConfigWINSServer OBJECT-TYPE
        SYNTAX  CifsConfigWINSServerTC
        MAX-ACCESS  read-only
        STATUS  current
        DESCRIPTION "CIFS WINS server"
        ::= { cifsConfig 2 }

    cifsConfigNetBIOSHostname OBJECT-TYPE
        SYNTAX  CifsConfigNetBIOSHostnameTC
        MAX-ACCESS  read-only
        STATUS  current
        DESCRIPTION "CIFS Net BIOS hostname"
        ::= { cifsConfig 3 }

    cifsConfigDomainController OBJECT-TYPE
        SYNTAX  CifsConfigDomainControllerTC
        MAX-ACCESS  read-only
        STATUS  current
        DESCRIPTION "CIFS domain controller"
        ::= { cifsConfig 4 }

    cifsConfigDNS OBJECT-TYPE
        SYNTAX  CifsConfigDNSTC
        MAX-ACCESS  read-only
        STATUS  current
        DESCRIPTION "CIFS DNS server"
        ::= { cifsConfig 5 }

    cifsConfigGroupName OBJECT-TYPE
        SYNTAX  CifsConfigGroupNameTC
        MAX-ACCESS  read-only
        STATUS  current
        DESCRIPTION "CIFS configuration group name"
        ::= { cifsConfig 6 }

-- **********************************************************************
--
-- cifsShare
-- ====================
--
-- dataDomainMib                (1.3.6.1.4.1.19746)
--   dataDomainMibObjects       (1.3.6.1.4.1.19746.1)
--     cifs                     (1.3.6.1.4.1.19746.1.10)
--       cifsShare              (1.3.6.1.4.1.19746.1.10.3)
--
-- **********************************************************************

    cifsShare		    OBJECT IDENTIFIER ::= { cifs 3 }

    cifsShareTable OBJECT-TYPE
        SYNTAX  SEQUENCE OF CifsShareEntry
        MAX-ACCESS  not-accessible
        STATUS  current
        DESCRIPTION
            "A table containing entries of CifsShareEntry."
        ::= { cifsShare 1 }

    cifsShareEntry OBJECT-TYPE
        SYNTAX  CifsShareEntry
        MAX-ACCESS  not-accessible
        STATUS  current
        DESCRIPTION
        "cifsShareTable Row Description"
        INDEX { cifsShareIndex }
        ::= { cifsShareTable 1 }

    CifsShareEntry ::= SEQUENCE {
        cifsShareIndex          CifsShareIndexTC,
        cifsShareName           CifsShareNameTC,
        cifsSharePath           CifsSharePathTC,
        cifsShareClients        CifsShareClientsTC,
        cifsShareUser           CifsShareUserTC,
        cifsShareComment        CifsShareCommentTC,
        cifsShareBrowsing       CifsShareBrowsingTC,
        cifsShareWriteable      CifsShareWriteableTC,
        cifsShareMaxConnection  CifsShareMaxConnectionTC
    }

    cifsShareIndex OBJECT-TYPE
        SYNTAX  CifsShareIndexTC 
        MAX-ACCESS  not-accessible
        STATUS  current
        DESCRIPTION
            "CIFS share index"
        ::= { cifsShareEntry 1 }

    cifsShareName OBJECT-TYPE
        SYNTAX  CifsShareNameTC 
        MAX-ACCESS  read-only 
        STATUS  current
        DESCRIPTION
            "CIFS share name"
        ::= { cifsShareEntry 2 }

    cifsSharePath OBJECT-TYPE
        SYNTAX  CifsSharePathTC 
        MAX-ACCESS  read-only 
        STATUS  current
        DESCRIPTION
            "CIFS share path"
        ::= { cifsShareEntry 3 }

    cifsShareClients OBJECT-TYPE
        SYNTAX  CifsShareClientsTC 
        MAX-ACCESS  read-only 
        STATUS  current
        DESCRIPTION
            "CIFS share clients"
        ::= { cifsShareEntry 4 }

    cifsShareUser OBJECT-TYPE
        SYNTAX  CifsShareUserTC 
        MAX-ACCESS  read-only 
        STATUS  current
        DESCRIPTION
            "CIFS share user"
        ::= { cifsShareEntry 5 }

    cifsShareComment OBJECT-TYPE
        SYNTAX  CifsShareCommentTC 
        MAX-ACCESS  read-only 
        STATUS  current
        DESCRIPTION
            "CIFS share comment"
        ::= { cifsShareEntry 6 }

    cifsShareBrowsing OBJECT-TYPE
        SYNTAX  CifsShareBrowsingTC 
        MAX-ACCESS  read-only 
        STATUS  current
        DESCRIPTION
            "CIFS share browsing"
        ::= { cifsShareEntry 7 }

    cifsShareWriteable OBJECT-TYPE
        SYNTAX  CifsShareWriteableTC 
        MAX-ACCESS  read-only 
        STATUS  current
        DESCRIPTION
            "CIFS share writeable"
        ::= { cifsShareEntry 8 }

    cifsShareMaxConnection OBJECT-TYPE
        SYNTAX  CifsShareMaxConnectionTC 
        MAX-ACCESS  read-only 
        STATUS  current
        DESCRIPTION
            "CIFS share maximum connection"
        ::= { cifsShareEntry 9 }

-- **********************************************************************
--
-- cifsOptions
-- ====================
--
-- dataDomainMib                (1.3.6.1.4.1.19746)
--   dataDomainMibObjects       (1.3.6.1.4.1.19746.1)
--     cifs                     (1.3.6.1.4.1.19746.1.10)
--       cifsOptions              (1.3.6.1.4.1.19746.1.10.5)
--
-- **********************************************************************

    cifsOptions		    OBJECT IDENTIFIER ::= { cifs 5 }

    cifsOptionsTable OBJECT-TYPE
        SYNTAX  SEQUENCE OF CifsOptionsEntry
        MAX-ACCESS  not-accessible
        STATUS  current
        DESCRIPTION
            "A table containing entries of CifsOptionsEntry."
        ::= { cifsOptions 1 }

    cifsOptionsEntry OBJECT-TYPE
        SYNTAX  CifsOptionsEntry
        MAX-ACCESS  not-accessible
        STATUS  current
        DESCRIPTION
        "cifsOptionsTable Row Description"
        INDEX { cifsOptionsIndex }
        ::= { cifsOptionsTable 1 }

    CifsOptionsEntry ::= SEQUENCE {
        cifsOptionsIndex          CifsOptionsIndexTC,
        cifsOptionsName           CifsOptionsNameTC,
        cifsOptionsValue           CifsOptionsValueTC
    }

    cifsOptionsIndex OBJECT-TYPE
        SYNTAX  CifsOptionsIndexTC 
        MAX-ACCESS  not-accessible
        STATUS  current
        DESCRIPTION
            "CIFS Options index"
        ::= { cifsOptionsEntry 1 }

    cifsOptionsName OBJECT-TYPE
        SYNTAX  CifsOptionsNameTC 
        MAX-ACCESS  read-only 
        STATUS  current
        DESCRIPTION
            "CIFS Options name"
        ::= { cifsOptionsEntry 2 }

    cifsOptionsValue OBJECT-TYPE
        SYNTAX  CifsOptionsValueTC 
        MAX-ACCESS  read-only 
        STATUS  current
        DESCRIPTION
            "CIFS Options Value"
        ::= { cifsOptionsEntry 3 }


-- **********************************************************************
--
-- vtlProperties 
-- ====================
--
-- dataDomainMib                (1.3.6.1.4.1.19746)
--   dataDomainMibObjects       (1.3.6.1.4.1.19746.1)
--     vtl                      (1.3.6.1.4.1.19746.1.11)
--       vtlProperties          (1.3.6.1.4.1.19746.1.11.1)
--         vtlAdminState        (1.3.6.1.4.1.19746.1.11.1.1)
--         vtlProcessState      (1.3.6.1.4.1.19746.1.11.1.2)
--
-- **********************************************************************

    vtlProperties		    OBJECT IDENTIFIER ::= { vtl 1 }

    vtlAdminState OBJECT-TYPE
        SYNTAX  VtlAdminStateTC
        MAX-ACCESS  read-only
        STATUS  current
        DESCRIPTION "State of VTL administration"
        ::= { vtlProperties 1 }

    vtlProcessState OBJECT-TYPE
        SYNTAX  VtlProcessStateTC
        MAX-ACCESS  read-only
        STATUS  current
        DESCRIPTION "State of VTL process"
        ::= { vtlProperties 2 }

-- **********************************************************************
--
-- vtlLibrary
-- ====================
--
-- dataDomainMib                (1.3.6.1.4.1.19746)
--   dataDomainMibObjects       (1.3.6.1.4.1.19746.1)
--     vtl                      (1.3.6.1.4.1.19746.1.11)
--       vtlConfiguration       (1.3.6.1.4.1.19746.1.11.2)
--         vtlLibrary           (1.3.6.1.4.1.19746.1.11.2.1)
--
-- **********************************************************************

    vtlConfiguration		    OBJECT IDENTIFIER ::= { vtl 2 }
    vtlLibrary		            OBJECT IDENTIFIER ::= { vtlConfiguration 1 }


    vtlLibraryTable OBJECT-TYPE
        SYNTAX  SEQUENCE OF VtlLibraryEntry
        MAX-ACCESS  not-accessible
        STATUS  current
        DESCRIPTION
            "A table containing entries of VtlLibraryEntry."
        ::= { vtlLibrary 1 }

    vtlLibraryEntry OBJECT-TYPE
        SYNTAX  VtlLibraryEntry
        MAX-ACCESS  not-accessible
        STATUS  current
        DESCRIPTION
        "vtlLibraryTable Row Description"
        INDEX { vtlLibraryIndex }
        ::= { vtlLibraryTable 1 }

    VtlLibraryEntry ::= SEQUENCE {
        vtlLibraryIndex        VtlLibraryIndexTC,
        vtlLibraryName         VtlLibraryNameTC,
        vtlLibraryVendor       VtlLibraryVendorTC,
        vtlLibraryModel        VtlLibraryModelTC,
        vtlLibraryRevision     VtlLibraryRevisionTC,
        vtlLibrarySerial       VtlLibrarySerialTC,
        vtlLibraryTotalDrives  VtlLibraryTotalDrivesTC,
        vtlLibraryTotalSlots   VtlLibraryTotalSlotsTC,
        vtlLibraryTotalCaps    VtlLibraryTotalCapsTC,
        vtlLibraryStatus       VtlLibraryStatusTC
    }

    vtlLibraryIndex OBJECT-TYPE
        SYNTAX  VtlLibraryIndexTC 
        MAX-ACCESS  not-accessible
        STATUS  current
        DESCRIPTION
            "VTL Library index"
        ::= { vtlLibraryEntry 1 }

    vtlLibraryName OBJECT-TYPE
        SYNTAX  VtlLibraryNameTC 
        MAX-ACCESS  read-only 
        STATUS  current
        DESCRIPTION
            "VTL library name"
        ::= { vtlLibraryEntry 2 }

    vtlLibraryVendor OBJECT-TYPE
        SYNTAX  VtlLibraryVendorTC 
        MAX-ACCESS  read-only 
        STATUS  current
        DESCRIPTION
            "VTL library vendor"
        ::= { vtlLibraryEntry 3 }

    vtlLibraryModel OBJECT-TYPE
        SYNTAX  VtlLibraryModelTC 
        MAX-ACCESS  read-only 
        STATUS  current
        DESCRIPTION
            "VTL library model"
        ::= { vtlLibraryEntry 4 }

    vtlLibraryRevision OBJECT-TYPE
        SYNTAX  VtlLibraryRevisionTC 
        MAX-ACCESS  read-only 
        STATUS  current
        DESCRIPTION
            "VTL library revision"
        ::= { vtlLibraryEntry 5 }

    vtlLibrarySerial OBJECT-TYPE
        SYNTAX  VtlLibrarySerialTC 
        MAX-ACCESS  read-only 
        STATUS  current
        DESCRIPTION
            "VTL library serial"
        ::= { vtlLibraryEntry 6 }

    vtlLibraryTotalDrives OBJECT-TYPE
        SYNTAX  VtlLibraryTotalDrivesTC 
        MAX-ACCESS  read-only 
        STATUS  current
        DESCRIPTION
            "VTL library total drives"
        ::= { vtlLibraryEntry 7 }

    vtlLibraryTotalSlots OBJECT-TYPE
        SYNTAX  VtlLibraryTotalSlotsTC 
        MAX-ACCESS  read-only 
        STATUS  current
        DESCRIPTION
            "VTL library total slots"
        ::= { vtlLibraryEntry 8 }

    vtlLibraryTotalCaps OBJECT-TYPE
        SYNTAX  VtlLibraryTotalCapsTC 
        MAX-ACCESS  read-only 
        STATUS  current
        DESCRIPTION
            "VTL library total caps"
        ::= { vtlLibraryEntry 9 }

    vtlLibraryStatus OBJECT-TYPE
        SYNTAX  VtlLibraryStatusTC
        MAX-ACCESS  read-only 
        STATUS  current
        DESCRIPTION
            "VTL library status"
        ::= { vtlLibraryEntry 10 }

-- **********************************************************************
--
-- vtlDrive
-- ====================
--
-- dataDomainMib                (1.3.6.1.4.1.19746)
--   dataDomainMibObjects       (1.3.6.1.4.1.19746.1)
--     vtl                      (1.3.6.1.4.1.19746.1.11)
--       vtlConfiguration       (1.3.6.1.4.1.19746.1.11.2)
--         vtlDrive             (1.3.6.1.4.1.19746.1.11.2.2)
--
-- **********************************************************************

    vtlDrive		            OBJECT IDENTIFIER ::= { vtlConfiguration 2 }

    vtlDriveTable OBJECT-TYPE
        SYNTAX  SEQUENCE OF VtlDriveEntry
        MAX-ACCESS  not-accessible
        STATUS  current
        DESCRIPTION
            "A table containing entries of VtlDriveEntry."
        ::= { vtlDrive 1 }

    vtlDriveEntry OBJECT-TYPE
        SYNTAX  VtlDriveEntry
        MAX-ACCESS  not-accessible
        STATUS  current
        DESCRIPTION
        "vtlDriveTable Row Description"
        INDEX { vtlDriveIndex }
        ::= { vtlDriveTable 1 }

    VtlDriveEntry ::= SEQUENCE {
        vtlDriveIndex        VtlDriveIndexTC,
        vtlDriveName         VtlDriveNameTC,
        vtlDriveVendor       VtlDriveVendorTC,
        vtlDriveModel        VtlDriveModelTC,
        vtlDriveRevision     VtlDriveRevisionTC,
        vtlDriveSerial       VtlDriveSerialTC,
        vtlDriveLibraryName  VtlLibraryNameTC,
        vtlDriveStatus       VtlDriveStatusTC,
        vtlDriveTapeVolume   VtlDriveTapeVolumeTC
    }

    vtlDriveIndex OBJECT-TYPE
        SYNTAX  VtlDriveIndexTC 
        MAX-ACCESS  not-accessible
        STATUS  current
        DESCRIPTION
            "VTL drive index"
        ::= { vtlDriveEntry 1 }

    vtlDriveName OBJECT-TYPE
        SYNTAX  VtlDriveNameTC 
        MAX-ACCESS  read-only 
        STATUS  current
        DESCRIPTION
            "VTL drive name"
        ::= { vtlDriveEntry 2 }

    vtlDriveVendor OBJECT-TYPE
        SYNTAX  VtlDriveVendorTC 
        MAX-ACCESS  read-only 
        STATUS  current
        DESCRIPTION
            "VTL drive vendor"
        ::= { vtlDriveEntry 3 }

    vtlDriveModel OBJECT-TYPE
        SYNTAX  VtlDriveModelTC 
        MAX-ACCESS  read-only 
        STATUS  current
        DESCRIPTION
            "VTL drive model"
        ::= { vtlDriveEntry 4 }

    vtlDriveRevision OBJECT-TYPE
        SYNTAX  VtlDriveRevisionTC 
        MAX-ACCESS  read-only 
        STATUS  current
        DESCRIPTION
            "VTL drive revision"
        ::= { vtlDriveEntry 5 }

    vtlDriveSerial OBJECT-TYPE
        SYNTAX  VtlDriveSerialTC 
        MAX-ACCESS  read-only 
        STATUS  current
        DESCRIPTION
            "VTL drive serial"
        ::= { vtlDriveEntry 6 }

    vtlDriveLibraryName OBJECT-TYPE
        SYNTAX  VtlLibraryNameTC 
        MAX-ACCESS  read-only 
        STATUS  current
        DESCRIPTION
            "VTL drive library name"
        ::= { vtlDriveEntry 7 }

    vtlDriveStatus OBJECT-TYPE
        SYNTAX  VtlDriveStatusTC 
        MAX-ACCESS  read-only 
        STATUS  current
        DESCRIPTION
            "VTL drive status"
        ::= { vtlDriveEntry 8 }

    vtlDriveTapeVolume OBJECT-TYPE
        SYNTAX  VtlDriveTapeVolumeTC
        MAX-ACCESS  read-only 
        STATUS  current
        DESCRIPTION
            "VTL drive tape volume"
        ::= { vtlDriveEntry 9 }


-- **********************************************************************
--
-- vtlPort
-- ====================
--
-- dataDomainMib                (1.3.6.1.4.1.19746)
--   dataDomainMibObjects       (1.3.6.1.4.1.19746.1)
--     vtl                      (1.3.6.1.4.1.19746.1.11)
--       vtlConfiguration       (1.3.6.1.4.1.19746.1.11.2)
--         vtlPort             (1.3.6.1.4.1.19746.1.11.2.3)
--
-- **********************************************************************

    vtlPort		            OBJECT IDENTIFIER ::= { vtlConfiguration 3 }

    vtlPortTable OBJECT-TYPE
        SYNTAX  SEQUENCE OF VtlPortEntry
        MAX-ACCESS  not-accessible
        STATUS  current
        DESCRIPTION
            "A table containing entries of VtlPortEntry."
        ::= { vtlPort 1 }

    vtlPortEntry OBJECT-TYPE
        SYNTAX  VtlPortEntry
        MAX-ACCESS  not-accessible
        STATUS  current
        DESCRIPTION
        "vtlPortTable Row Description"
        INDEX { vtlPortIndex }
        ::= { vtlPortTable 1 }

    VtlPortEntry ::= SEQUENCE {
        vtlPortIndex            VtlPortIndexTC,
        vtlPortName             VtlPortNameTC,
        vtlPortID               VtlPortIDTC,
        vtlPortModel            VtlPortModelTC,
        vtlPortFirmware         VtlPortFirmwareTC,
        vtlPortWWNN             VtlPortWWNNTC,
        vtlPortWWPN             VtlPortWWPNTC,
        vtlPortConnectionType   VtlPortConnectionTypeTC,
        vtlPortSpeed            VtlPortSpeedTC,
        vtlPortTapeEnabled          VtlPortEnabledTC,
        vtlPortTapeStatus           VtlPortStatusTC,
        vtlPortTrapIndex        VtlPortIndexTC
    }

    vtlPortIndex OBJECT-TYPE
        SYNTAX  VtlPortIndexTC 
        MAX-ACCESS  not-accessible
        STATUS  current
        DESCRIPTION
            "VTL Port index"
        ::= { vtlPortEntry 1 }

    vtlPortName OBJECT-TYPE
        SYNTAX  VtlPortNameTC 
        MAX-ACCESS  read-only 
        STATUS  current
        DESCRIPTION
            "VTL Port name"
        ::= { vtlPortEntry 2 }

    vtlPortID OBJECT-TYPE
        SYNTAX  VtlPortIDTC 
        MAX-ACCESS  read-only 
        STATUS  current
        DESCRIPTION
            "VTL Port ID"
        ::= { vtlPortEntry 3 }

    vtlPortModel OBJECT-TYPE
        SYNTAX  VtlPortModelTC 
        MAX-ACCESS  read-only 
        STATUS  current
        DESCRIPTION
            "VTL Port model"
        ::= { vtlPortEntry 4 }
    
    vtlPortFirmware OBJECT-TYPE
        SYNTAX  VtlPortFirmwareTC 
        MAX-ACCESS  read-only 
        STATUS  current
        DESCRIPTION
            "VTL Port Firmware Version"
        ::= { vtlPortEntry 5 }

    vtlPortWWNN OBJECT-TYPE
        SYNTAX  VtlPortWWNNTC 
        MAX-ACCESS  read-only 
        STATUS  current
        DESCRIPTION
            "VTL Port WWNN address"
        ::= { vtlPortEntry 6 }

    vtlPortWWPN OBJECT-TYPE
        SYNTAX  VtlPortWWPNTC 
        MAX-ACCESS  read-only 
        STATUS  current
        DESCRIPTION
            "VTL Port WWPN Address"
        ::= { vtlPortEntry 7 }

    vtlPortConnectionType OBJECT-TYPE
        SYNTAX  VtlPortConnectionTypeTC 
        MAX-ACCESS  read-only 
        STATUS  current
        DESCRIPTION
            "VTL Port Connection Type"
        ::= { vtlPortEntry 8 }

    vtlPortSpeed OBJECT-TYPE
        SYNTAX  VtlPortSpeedTC 
        MAX-ACCESS  read-only 
        STATUS  current
        DESCRIPTION
            "VTL Port Speed in Gibs"
        ::= { vtlPortEntry 9 }

    vtlPortEnabled OBJECT-TYPE
        SYNTAX  VtlPortEnabledTC
        MAX-ACCESS  read-only 
        STATUS  current
        DESCRIPTION
            "VTL Port Enabled"
        ::= { vtlPortEntry 10 }

    vtlPortStatus OBJECT-TYPE
        SYNTAX  VtlPortStatusTC
        MAX-ACCESS  read-only 
        STATUS  current
        DESCRIPTION
            "VTL Port Status"
        ::= { vtlPortEntry 11 }
    
    vtlPortTrapIndex OBJECT-TYPE
        SYNTAX  VtlPortIndexTC 
        MAX-ACCESS  read-only
        STATUS  current
        DESCRIPTION
            "VTL Port index"
        ::= { vtlPortEntry 12 }

-- **********************************************************************
--
-- vtlTape
-- ====================
--
-- dataDomainMib                (1.3.6.1.4.1.19746)
--   dataDomainMibObjects       (1.3.6.1.4.1.19746.1)
--     vtl                      (1.3.6.1.4.1.19746.1.11)
--       vtlConfiguration       (1.3.6.1.4.1.19746.1.11.2)
--         vtlTape              (1.3.6.1.4.1.19746.1.11.2.4)
--
-- **********************************************************************

    vtlTape		            OBJECT IDENTIFIER ::= { vtlConfiguration 4 }

    vtlTapeTable OBJECT-TYPE
        SYNTAX  SEQUENCE OF VtlTapeEntry
        MAX-ACCESS  not-accessible
        STATUS  current
        DESCRIPTION
            "A table containing entries of VtlTapeEntry."
        ::= { vtlTape 1 }

    vtlTapeEntry OBJECT-TYPE
        SYNTAX  VtlTapeEntry
        MAX-ACCESS  not-accessible
        STATUS  current
        DESCRIPTION
        "vtlTapeTable Row Description"
        INDEX { vtlTapeIndex }
        ::= { vtlTapeTable 1 }

    VtlTapeEntry ::= SEQUENCE {
        vtlTapeIndex          VtlTapeIndexTC,
        vtlTapeBarCode        VtlTapeBarCodeTC,
        vtlTapePool           VtlTapePoolTC,
        vtlTapeLocation       VtlTapeLocationTC,
        vtlTapeState          VtlTapeStateTC,
        vtlTapeSize           VtlTapeSizeTC,
        vtlTapeUsed           VtlTapeUsedTC,
        vtlTapeComp           VtlTapeCompTC,
        vtlTapeModTime        VtlTapeModTimeTC
    }

    vtlTapeIndex OBJECT-TYPE
        SYNTAX  VtlTapeIndexTC 
        MAX-ACCESS  not-accessible
        STATUS  current
        DESCRIPTION
            "VTL Tape index"
        ::= { vtlTapeEntry 1 }

    vtlTapeBarCode OBJECT-TYPE
        SYNTAX  VtlTapeBarCodeTC 
        MAX-ACCESS  read-only 
        STATUS  current
        DESCRIPTION
            "VTL Tape BarCode"
        ::= { vtlTapeEntry 2 }

    vtlTapePool OBJECT-TYPE
        SYNTAX  VtlTapePoolTC 
        MAX-ACCESS  read-only 
        STATUS  current
        DESCRIPTION
            "VTL Tape Pool"
        ::= { vtlTapeEntry 3 }
    
    vtlTapeLocation OBJECT-TYPE
        SYNTAX  VtlTapeLocationTC 
        MAX-ACCESS  read-only 
        STATUS  current
        DESCRIPTION
            "VTL Tape Location"
        ::= { vtlTapeEntry 4 }


    vtlTapeState OBJECT-TYPE
        SYNTAX  VtlTapeStateTC 
        MAX-ACCESS  read-only 
        STATUS  current
        DESCRIPTION
            "VTL Tape State"
        ::= { vtlTapeEntry 5 }

    vtlTapeSize OBJECT-TYPE
        SYNTAX  VtlTapeSizeTC 
        MAX-ACCESS  read-only 
        STATUS  current
        DESCRIPTION
            "VTL Tape Size"
        ::= { vtlTapeEntry 6 }

    vtlTapeUsed OBJECT-TYPE
        SYNTAX  VtlTapeUsedTC 
        MAX-ACCESS  read-only 
        STATUS  current
        DESCRIPTION
            "VTL Tape Used"
        ::= { vtlTapeEntry 7 }

    vtlTapeComp OBJECT-TYPE
        SYNTAX  VtlTapeCompTC 
        MAX-ACCESS  read-only 
        STATUS  current
        DESCRIPTION
            "VTL Tape Compression"
        ::= { vtlTapeEntry 8 }

    vtlTapeModTime OBJECT-TYPE
        SYNTAX  VtlTapeModTimeTC 
        MAX-ACCESS  read-only 
        STATUS  current
        DESCRIPTION
            "VTL Tape status"
        ::= { vtlTapeEntry 9 }


-- **********************************************************************
--
-- vtlStats
-- ====================
--
-- dataDomainMib                (1.3.6.1.4.1.19746)
--   dataDomainMibObjects       (1.3.6.1.4.1.19746.1)
--     vtl                      (1.3.6.1.4.1.19746.1.11)
--       vtlStats                  (1.3.6.1.4.1.19746.1.11.3)
--
-- **********************************************************************

    vtlStats		      OBJECT IDENTIFIER ::= { vtl 3 }

    vtlStatsTable OBJECT-TYPE
        SYNTAX  SEQUENCE OF VtlStatsEntry
        MAX-ACCESS  not-accessible
        STATUS  current
        DESCRIPTION
            "A table containing entries of VtlStatsEntry."
        ::= { vtlStats 1 }

    vtlStatsEntry OBJECT-TYPE
        SYNTAX  VtlStatsEntry
        MAX-ACCESS  not-accessible
        STATUS  current
        DESCRIPTION
        "vtlStatsTable Row Description"
        INDEX { vtlStatsIndex }
        ::= { vtlStatsTable 1 }

    VtlStatsEntry ::= SEQUENCE {
        vtlStatsIndex                   VtlStatsIndexTC,
        vtlStatsPort                    VtlStatsPortTC,
        vtlStatsConrolCommands          VtlStatsConrolCommandsTC,
        vtlStatsWriteCommands           VtlStatsWriteCommandsTC,
        vtlStatsReadCommands            VtlStatsReadCommandsTC,
        vtlStatsIn                      VtlStatsInTC,
        vtlStatsOut                     VtlStatsOutTC,
        vtlStatsLinkFailures            VtlStatsLinkFailuresTC,
        vtlStatsLIPCount                VtlStatsLIPCountTC,
        vtlStatsSyncLosses              VtlStatsSyncLossesTC,
        vtlStatsSignalLosses            VtlStatsSignalLossesTC,
        vtlStatsPrimSeqProtoErrors      VtlStatsPrimSeqProtoErrorsTC,
        vtlStatsInvalidTxWords          VtlStatsInvalidTxWordsTC,
        vtlStatsInvalidCRCs             VtlStatsInvalidCRCsTC

    }

    vtlStatsIndex OBJECT-TYPE
        SYNTAX  VtlStatsIndexTC 
        MAX-ACCESS  not-accessible
        STATUS  current
        DESCRIPTION
            "VTL Stats index"
        ::= { vtlStatsEntry 1 }

    vtlStatsPort OBJECT-TYPE
        SYNTAX  VtlStatsPortTC 
        MAX-ACCESS  read-only 
        STATUS  current
        DESCRIPTION
            "VTL Stats Port"
        ::= { vtlStatsEntry 2 }

    vtlStatsConrolCommands OBJECT-TYPE
        SYNTAX  VtlStatsConrolCommandsTC 
        MAX-ACCESS  read-only 
        STATUS  current
        DESCRIPTION
            "VTL Stats ConrolCommands"
        ::= { vtlStatsEntry 3 }

    vtlStatsWriteCommands OBJECT-TYPE
        SYNTAX  VtlStatsWriteCommandsTC 
        MAX-ACCESS  read-only 
        STATUS  current
        DESCRIPTION
            "VTL Stats WriteCommands"
        ::= { vtlStatsEntry 4 }

    vtlStatsReadCommands OBJECT-TYPE
        SYNTAX  VtlStatsReadCommandsTC 
        MAX-ACCESS  read-only 
        STATUS  current
        DESCRIPTION
            "VTL Stats ReadCommands"
        ::= { vtlStatsEntry 5 }

    vtlStatsIn OBJECT-TYPE
        SYNTAX  VtlStatsInTC 
        MAX-ACCESS  read-only 
        STATUS  current
        DESCRIPTION
            "VTL Stats In"
        ::= { vtlStatsEntry 6 }

    vtlStatsOut OBJECT-TYPE
        SYNTAX  VtlStatsOutTC 
        MAX-ACCESS  read-only 
        STATUS  current
        DESCRIPTION
            "VTL Stats Outression"
        ::= { vtlStatsEntry 7 }

    vtlStatsLinkFailures OBJECT-TYPE
        SYNTAX  VtlStatsLinkFailuresTC 
        MAX-ACCESS  read-only 
        STATUS  current
        DESCRIPTION
            "VTL Stats status"
        ::= { vtlStatsEntry 8 }

    vtlStatsLIPCount OBJECT-TYPE
        SYNTAX  VtlStatsLIPCountTC 
        MAX-ACCESS  read-only 
        STATUS  current
        DESCRIPTION
            "VTL Stats LIPCount"
        ::= { vtlStatsEntry 9 }

    vtlStatsSyncLosses OBJECT-TYPE
        SYNTAX  VtlStatsSyncLossesTC 
        MAX-ACCESS  read-only 
        STATUS  current
        DESCRIPTION
            "VTL Stats SyncLosses"
        ::= { vtlStatsEntry 10 }

    vtlStatsSignalLosses OBJECT-TYPE
        SYNTAX  VtlStatsSignalLossesTC 
        MAX-ACCESS  read-only 
        STATUS  current
        DESCRIPTION
            "VTL Stats SignalLosses"
        ::= { vtlStatsEntry 11 }

    vtlStatsPrimSeqProtoErrors OBJECT-TYPE
        SYNTAX  VtlStatsPrimSeqProtoErrorsTC 
        MAX-ACCESS  read-only 
        STATUS  current
        DESCRIPTION
            "VTL Stats PrimSeqProtoErrors"
        ::= { vtlStatsEntry 12 }

    vtlStatsInvalidTxWords OBJECT-TYPE
        SYNTAX  VtlStatsInvalidTxWordsTC 
        MAX-ACCESS  read-only 
        STATUS  current
        DESCRIPTION
            "VTL Stats InvalidTxWordsression"
        ::= { vtlStatsEntry 13 }

    vtlStatsInvalidCRCs OBJECT-TYPE
        SYNTAX  VtlStatsInvalidCRCsTC 
        MAX-ACCESS  read-only 
        STATUS  current
        DESCRIPTION
            "VTL Stats 1status"
        ::= { vtlStatsEntry 14 }


-- **********************************************************************
--
-- ddboostProperties 
-- ====================
--
-- dataDomainMib                (1.3.6.1.4.1.19746)
--   dataDomainMibObjects       (1.3.6.1.4.1.19746.1)
--     ddboost                      (1.3.6.1.4.1.19746.1.12)
--       ddboostProperties          (1.3.6.1.4.1.19746.1.12.1)
--         ddboostStatus            (1.3.6.1.4.1.19746.1.12.1.1)
--         ddboostUser              (1.3.6.1.4.1.19746.1.12.1.2)
--
-- **********************************************************************

    ddboostProperties		    OBJECT IDENTIFIER ::= { ddboost 1 }

    ddboostStatus OBJECT-TYPE
        SYNTAX  DDboostStatusTC 
        MAX-ACCESS  read-only
        STATUS  current
        DESCRIPTION "DDBOOST Status"
        ::= { ddboostProperties 1 }

    ddboostUser OBJECT-TYPE
        SYNTAX  DDboostUserTC
        MAX-ACCESS  read-only
        STATUS  current
        DESCRIPTION "DDBOOST User"
        ::= { ddboostProperties 2 }

-- **********************************************************************
--
-- ddboostProperties 
-- ====================
--
-- dataDomainMib                (1.3.6.1.4.1.19746)
--   dataDomainMibObjects       (1.3.6.1.4.1.19746.1)
--     ddboost                      (1.3.6.1.4.1.19746.1.12)
--       ddboostStats               (1.3.6.1.4.1.19746.1.12.2)
--
-- **********************************************************************

    ddboostStats		    OBJECT IDENTIFIER ::= { ddboost 2 }

     ddboostStatsTable OBJECT-TYPE
        SYNTAX  SEQUENCE OF DdboostStatsEntry
        MAX-ACCESS  not-accessible
        STATUS  current
        DESCRIPTION
            "DDBOOST stats table containing byte statistics information for DDBOOST"
        ::= { ddboostStats 1 }

    ddboostStatsEntry OBJECT-TYPE
        SYNTAX  DdboostStatsEntry
        MAX-ACCESS  not-accessible
        STATUS  current
        DESCRIPTION
        "ddboostStatsTable Row Entry"
        INDEX { ddboostStatsIndex }
        ::= { ddboostStatsTable 1 }

     DdboostStatsEntry ::= SEQUENCE {
        ddboostStatsIndex                       DDboostStatsIndexTC,
        ddboostPreCompKBytesPerSecond	    KBytesPerSecond,
	ddboostPostCompKBytesPerSecond	    KBytesPerSecond,
	ddboostNetworkKBytesPerSecond	    KBytesPerSecond,
	ddboostReadKBytesPerSecond	            KBytesPerSecond
    }

     ddboostStatsIndex OBJECT-TYPE
        SYNTAX  DDboostStatsIndexTC 
        MAX-ACCESS  not-accessible
        STATUS  current
        DESCRIPTION
            "ddboost Stats Table index"
        ::= { ddboostStatsEntry 1 }

    ddboostPreCompKBytesPerSecond OBJECT-TYPE
        SYNTAX   KBytesPerSecond
        MAX-ACCESS  read-only
        STATUS  current
        DESCRIPTION
            "Number of pre-compressed (logical) bytes received"
        ::= { ddboostStatsEntry 2 }

    ddboostPostCompKBytesPerSecond OBJECT-TYPE
        SYNTAX  KBytesPerSecond 
        MAX-ACCESS  read-only
        STATUS  current
        DESCRIPTION
            "number of pddboost local compression bytes received"
        ::= { ddboostStatsEntry 3 }

    ddboostNetworkKBytesPerSecond OBJECT-TYPE
        SYNTAX  KBytesPerSecond 
        MAX-ACCESS  read-only
        STATUS  current
        DESCRIPTION
            "Number of physical network bytes received"
        ::= { ddboostStatsEntry 4 }

    ddboostReadKBytesPerSecond OBJECT-TYPE
        SYNTAX  KBytesPerSecond 
        MAX-ACCESS  read-only
        STATUS  current
        DESCRIPTION
            "Number of bytes read"
        ::= { ddboostStatsEntry 5 }



-- **********************************************************************
--
-- systemProperties 
-- ==================
--
-- dataDomainMib        		(1.3.6.1.4.1.19746)
--   dataDomainMibObjects		(1.3.6.1.4.1.19746.1)
--	dataDomainSystem		(1.3.6.1.4.1.19746.1.13)
--	       systemProperties         (1.3.6.1.4.1.19746.1.1.13.1)
--
-- **********************************************************************

    systemProperties	    OBJECT IDENTIFIER ::= { dataDomainSystem 1 }

    systemSerialNumber OBJECT-TYPE
        SYNTAX  SystemSerialNumberTC 
        MAX-ACCESS  read-only
        STATUS  current
        DESCRIPTION "Serial Number of the System"
        ::= { systemProperties 1 }

-- **********************************************************************
--
-- artConfig
-- ====================
--
-- dataDomainMib                (1.3.6.1.4.1.19746)
--   dataDomainMibObjects       (1.3.6.1.4.1.19746.1)
--     art                     (1.3.6.1.4.1.19746.1.14)
--       artConfig              (1.3.6.1.4.1.19746.1.14.1)
--
-- **********************************************************************

    artConfig		    OBJECT IDENTIFIER ::= { art 1 }

    artConfigTable OBJECT-TYPE
        SYNTAX  SEQUENCE OF ArtConfigEntry
        MAX-ACCESS  not-accessible
        STATUS  current
        DESCRIPTION
            "A table containing entries of artConfigEntry."
        ::= { artConfig 1 }

    artConfigEntry OBJECT-TYPE
        SYNTAX  ArtConfigEntry
        MAX-ACCESS  not-accessible
        STATUS  current
        DESCRIPTION
        "artConfigTable Row Description"
        INDEX { artConfigIndex }
        ::= { artConfigTable 1 }

    ArtConfigEntry ::= SEQUENCE {
        artConfigIndex                  DDMibTableIndexTC,
        artConfigStatus                 DDMibTableEnabledTC,
        artConfigMigrationSchedule      DDMibTableString128TC,
        artConfigDefaultAge             DDMibInteger32TC,
        artConfigFileSystemClean           DDMibTableEnabledTC,
        artConfigCompression            DDMibTableString32TC 
        
    }

    artConfigIndex OBJECT-TYPE
        SYNTAX  DDMibTableIndexTC 
        MAX-ACCESS  not-accessible
        STATUS  current
        DESCRIPTION
            "art Config index"
        ::= { artConfigEntry 1 }

    artConfigStatus OBJECT-TYPE
        SYNTAX  DDMibTableEnabledTC 
        MAX-ACCESS  read-only 
        STATUS  current
        DESCRIPTION
            "art Config Status"
        ::= { artConfigEntry 2 }

    artConfigMigrationSchedule OBJECT-TYPE
        SYNTAX  DDMibTableString128TC 
        MAX-ACCESS  read-only 
        STATUS  current
        DESCRIPTION
            "art Config Migration Schedule"
        ::= { artConfigEntry 3 }

    artConfigDefaultAge OBJECT-TYPE
        SYNTAX  DDMibInteger32TC
        MAX-ACCESS  read-only 
        STATUS  current
        DESCRIPTION
            "art Config Default Age threshold migration policy"
        ::= { artConfigEntry 4 }

    artConfigFileSystemClean OBJECT-TYPE
        SYNTAX  DDMibTableEnabledTC 
        MAX-ACCESS  read-only 
        STATUS  current
        DESCRIPTION
            "art Config file System Clean Required"
        ::= { artConfigEntry 5 }

    
    artConfigCompression OBJECT-TYPE
        SYNTAX  DDMibTableString32TC 
        MAX-ACCESS  read-only 
        STATUS  current
        DESCRIPTION
            "art Config local compression"
        ::= { artConfigEntry 6 }

    


-- **********************************************************************
--
-- artMigrationSchedule
-- ====================
--
-- dataDomainMib                (1.3.6.1.4.1.19746)
--   dataDomainMibObjects       (1.3.6.1.4.1.19746.1)
--     art                     (1.3.6.1.4.1.19746.1.14)
--       artMigrationSchedule             (1.3.6.1.4.1.19746.1.14.2)
--
-- **********************************************************************

    artMigrationSchedule		    OBJECT IDENTIFIER ::= { art 2 }

    artMigrationScheduleTable OBJECT-TYPE
        SYNTAX  SEQUENCE OF ArtMigrationScheduleEntry
        MAX-ACCESS  not-accessible
        STATUS  current
        DESCRIPTION
            "A table containing entries of artMigrationScheduleEntry."
        ::= { artMigrationSchedule 1 }

    artMigrationScheduleEntry OBJECT-TYPE
        SYNTAX  ArtMigrationScheduleEntry
        MAX-ACCESS  not-accessible
        STATUS  current
        DESCRIPTION
        "artMigrationScheduleTable Row Description"
        INDEX { artMigrationScheduleIndex }
        ::= { artMigrationScheduleTable 1 }

    ArtMigrationScheduleEntry ::= SEQUENCE {
        artMigrationScheduleIndex                  DDMibTableIndexTC,
        artMigrationScheduleSchedule               DDMibTableString512TC,
        artMigrationScheduleStatus                 DDMibInteger32TC
    }

    artMigrationScheduleIndex OBJECT-TYPE
        SYNTAX  DDMibTableIndexTC 
        MAX-ACCESS  not-accessible
        STATUS  current
        DESCRIPTION
            "art MigrationScheduleindex"
        ::= { artMigrationScheduleEntry 1 }

    artMigrationScheduleSchedule OBJECT-TYPE
        SYNTAX  DDMibTableString512TC 
        MAX-ACCESS  read-only 
        STATUS  current
        DESCRIPTION
            "art MigrationSchedule Description"
        ::= { artMigrationScheduleEntry 2 }

    artMigrationScheduleStatus OBJECT-TYPE
        SYNTAX  DDMibInteger32TC 
        MAX-ACCESS  read-only 
        STATUS  current
        DESCRIPTION
            "art MigrationSchedule Status"
        ::= { artMigrationScheduleEntry 3 }

-- **********************************************************************
--
-- artMigrationPolicy
-- ====================
--
-- dataDomainMib                (1.3.6.1.4.1.19746)
--   dataDomainMibObjects       (1.3.6.1.4.1.19746.1)
--     art                     (1.3.6.1.4.1.19746.1.14)
--       artMigrationPolicy              (1.3.6.1.4.1.19746.1.14.3)
--
-- **********************************************************************

    artMigrationPolicy		    OBJECT IDENTIFIER ::= { art 3 }

    artMigrationPolicyTable OBJECT-TYPE
        SYNTAX  SEQUENCE OF ArtMigrationPolicyEntry
        MAX-ACCESS  not-accessible
        STATUS  current
        DESCRIPTION
            "A table containing entries of artMigrationPolicyEntry."
        ::= { artMigrationPolicy 1 }

    artMigrationPolicyEntry OBJECT-TYPE
        SYNTAX  ArtMigrationPolicyEntry
        MAX-ACCESS  not-accessible
        STATUS  current
        DESCRIPTION
        "artMigrationPolicyTable Row Description"
        INDEX { artMigrationPolicyIndex }
        ::= { artMigrationPolicyTable 1 }

    ArtMigrationPolicyEntry ::= SEQUENCE {
        artMigrationPolicyIndex                  DDMibTableIndexTC,
        artMigrationPolicyMtreeName              DDMibTableString256TC,
        artMigrationPolicyDefaultAge             DDMibInteger32TC 
    }

    artMigrationPolicyIndex OBJECT-TYPE
        SYNTAX  DDMibTableIndexTC 
        MAX-ACCESS  not-accessible
        STATUS  current
        DESCRIPTION
            "art MigrationPolicy index"
        ::= { artMigrationPolicyEntry 1 }

    artMigrationPolicyMtreeName OBJECT-TYPE
        SYNTAX  DDMibTableString256TC 
        MAX-ACCESS  read-only 
        STATUS  current
        DESCRIPTION
            "art MigrationPolicy Mtree Name"
        ::= { artMigrationPolicyEntry 2 }

    artMigrationPolicyDefaultAge OBJECT-TYPE
        SYNTAX  DDMibInteger32TC 
        MAX-ACCESS  read-only 
        STATUS  current
        DESCRIPTION
            "art MigrationPolicy Default Age"
        ::= { artMigrationPolicyEntry 3 }

-- **********************************************************************
--
-- mtreeCompression
-- ====================
--
-- dataDomainMib                (1.3.6.1.4.1.19746)
--   dataDomainMibObjects       (1.3.6.1.4.1.19746.1)
--     mtree                     (1.3.6.1.4.1.19746.1.15)
--       mtreeCompression              (1.3.6.1.4.1.19746.1.15.1)
--
-- **********************************************************************

    mtreeCompression		    OBJECT IDENTIFIER ::= { mtree 1 }

    mtreeCompressionTable OBJECT-TYPE
        SYNTAX  SEQUENCE OF MtreeCompressionEntry
        MAX-ACCESS  not-accessible
        STATUS  current
        DESCRIPTION
            "A table containing entries of mtreeCompressionEntry."
        ::= { mtreeCompression 1 }

    mtreeCompressionEntry OBJECT-TYPE
        SYNTAX  MtreeCompressionEntry
        MAX-ACCESS  not-accessible
        STATUS  current
        DESCRIPTION
        "mtreeCompressionTable Row Description"
        INDEX { mtreeCompressionIndex }
        ::= { mtreeCompressionTable 1 }

    MtreeCompressionEntry ::= SEQUENCE {
        mtreeCompressionIndex                  DDMibTableIndexTC,
        mtreeCompressionMtreePath              DDMibTableString512TC,
        mtreeCompressionPreCompGib             DDMibTableSizeGibTC,
        mtreeCompressionPostCompGib            DDMibTableSizeGibTC,
        mtreeCompressionGlobalCompFactor       DDMibCompressionFactorTC,
        mtreeCompressionLocalCompFactor        DDMibCompressionFactorTC,
        mtreeCompressionPostTotalCompFactor    DDMibCompressionFactorTC,
        mtreeCompressionTimePeriod             DDMibTableString128TC
    }

    mtreeCompressionIndex OBJECT-TYPE
        SYNTAX  DDMibTableIndexTC 
        MAX-ACCESS  not-accessible
        STATUS  current
        DESCRIPTION
            "mtree Compression index"
        ::= { mtreeCompressionEntry 1 }

    mtreeCompressionMtreePath OBJECT-TYPE
        SYNTAX  DDMibTableString512TC 
        MAX-ACCESS  read-only 
        STATUS  current
        DESCRIPTION
            "mtree Compression Mtree Path"
        ::= { mtreeCompressionEntry 2 }

    mtreeCompressionPreCompGib OBJECT-TYPE
        SYNTAX  DDMibTableSizeGibTC
        MAX-ACCESS  read-only 
        STATUS  current
        DESCRIPTION
            "mtree Compression Pre comp giga bytes"
        ::= { mtreeCompressionEntry 3 }

     mtreeCompressionPostCompGib OBJECT-TYPE
        SYNTAX  DDMibTableSizeGibTC
        MAX-ACCESS  read-only
        STATUS  current
        DESCRIPTION
            "mtree Compression Post Comp Giga Bytes"
        ::= { mtreeCompressionEntry 4 }

    mtreeCompressionGlobalCompFactor OBJECT-TYPE
        SYNTAX  DDMibCompressionFactorTC
        MAX-ACCESS  read-only 
        STATUS  current
        DESCRIPTION
            "mtree Compression Global Comp Factor"
        ::= { mtreeCompressionEntry 5 }

    mtreeCompressionLocalCompFactor OBJECT-TYPE
        SYNTAX  DDMibCompressionFactorTC
        MAX-ACCESS read-only 
        STATUS  current
        DESCRIPTION
            "mtree Compression Local Comp Factor"
        ::= { mtreeCompressionEntry 6 }

    mtreeCompressionPostTotalCompFactor OBJECT-TYPE
        SYNTAX  DDMibCompressionFactorTC
        MAX-ACCESS  read-only 
        STATUS  current
        DESCRIPTION
            "mtree Compression Total Comp Factor"
        ::= { mtreeCompressionEntry 7 }

    
    mtreeCompressionTimePeriod    OBJECT-TYPE
        SYNTAX  DDMibTableString128TC
        MAX-ACCESS  read-only 
        STATUS  current
        DESCRIPTION
            "mtree Compression Time Period"
        ::= { mtreeCompressionEntry 8 }

    
-- **********************************************************************
--
-- mtreeList
-- ====================
--
-- dataDomainMib                (1.3.6.1.4.1.19746)
--   dataDomainMibObjects       (1.3.6.1.4.1.19746.1)
--     mtree                     (1.3.6.1.4.1.19746.1.15)
--       mtreeList              (1.3.6.1.4.1.19746.1.15.2)
--
-- **********************************************************************

    mtreeList		    OBJECT IDENTIFIER ::= { mtree 2 }

    mtreeListTable OBJECT-TYPE
        SYNTAX  SEQUENCE OF MtreeListEntry
        MAX-ACCESS  not-accessible
        STATUS  current
        DESCRIPTION
            "A table containing entries of mtreeListEntry."
        ::= { mtreeList 1 }

    mtreeListEntry OBJECT-TYPE
        SYNTAX  MtreeListEntry
        MAX-ACCESS  not-accessible
        STATUS  current
        DESCRIPTION
        "mtreeListTable Row Description"
        INDEX { mtreeListIndex }
        ::= { mtreeListTable 1 }

    MtreeListEntry ::= SEQUENCE {
        mtreeListIndex                  DDMibTableIndexTC,
        mtreeListMtreeName              DDMibTableString512TC,
        mtreeListPreCompGib             DDMibTableSizeGibTC,
        mtreeListStatus                 MtreeListStatusTC
    }

    mtreeListIndex OBJECT-TYPE
        SYNTAX  DDMibTableIndexTC 
        MAX-ACCESS  not-accessible
        STATUS  current
        DESCRIPTION
            "mtree List index"
        ::= { mtreeListEntry 1 }

    mtreeListMtreeName OBJECT-TYPE
        SYNTAX  DDMibTableString512TC 
        MAX-ACCESS  read-only 
        STATUS  current
        DESCRIPTION
            "mtree List Mtree Name"
        ::= { mtreeListEntry 2 }

    mtreeListPreCompGib OBJECT-TYPE
        SYNTAX  DDMibTableSizeGibTC
        MAX-ACCESS  read-only 
        STATUS  current
        DESCRIPTION
            "mtree List Pre comp giga bytes"
        ::= { mtreeListEntry 3 }

     mtreeListStatus OBJECT-TYPE
        SYNTAX  MtreeListStatusTC
        MAX-ACCESS read-only 
        STATUS  current
        DESCRIPTION
            "mtree List Status"
        ::= { mtreeListEntry 4 }


    
-- **********************************************************************
--
-- mtreeRetentionLock
-- ====================
--
-- dataDomainMib                (1.3.6.1.4.1.19746)
--   dataDomainMibObjects       (1.3.6.1.4.1.19746.1)
--     mtree                     (1.3.6.1.4.1.19746.1.15)
--       mtreeRetentionLock              (1.3.6.1.4.1.19746.1.15.4)
--
-- **********************************************************************

    mtreeRetentionLock		    OBJECT IDENTIFIER ::= { mtree 4 }

    mtreeRetentionLockTable OBJECT-TYPE
        SYNTAX  SEQUENCE OF MtreeRetentionLockEntry
        MAX-ACCESS  not-accessible
        STATUS  current
        DESCRIPTION
            "A table containing entries of mtreeRetentionLockEntry."
        ::= { mtreeRetentionLock 1 }

    mtreeRetentionLockEntry OBJECT-TYPE
        SYNTAX  MtreeRetentionLockEntry
        MAX-ACCESS  not-accessible
        STATUS  current
        DESCRIPTION
        "mtreeRetentionLockTable Row Description"
        INDEX { mtreeRetentionLockIndex }
        ::= { mtreeRetentionLockTable 1 }

    MtreeRetentionLockEntry ::= SEQUENCE {
        mtreeRetentionLockIndex                  DDMibTableIndexTC,
        mtreeRetentionLockMtreeName              DDMibTableString512TC,
        mtreeRetentionLockStatus                 MtreeRetentionLockStatusTC,
        mtreeRetentionLockUUID                   DDMibTableString32TC,
        mtreeRetentionLockMinRetentionPeriod     DDMibTableString32TC,
        mtreeRetentionLockMaxRetentionPeriod     DDMibTableString32TC
    }

    mtreeRetentionLockIndex OBJECT-TYPE
        SYNTAX  DDMibTableIndexTC 
        MAX-ACCESS  not-accessible
        STATUS  current
        DESCRIPTION
            "mtree RetentionLock index"
        ::= { mtreeRetentionLockEntry 1 }

    mtreeRetentionLockMtreeName OBJECT-TYPE
        SYNTAX  DDMibTableString512TC 
        MAX-ACCESS  read-only 
        STATUS  current
        DESCRIPTION
            "mtree RetentionLock Mtree Name"
        ::= { mtreeRetentionLockEntry 2 }

    mtreeRetentionLockStatus OBJECT-TYPE
        SYNTAX  MtreeRetentionLockStatusTC 
        MAX-ACCESS  read-only 
        STATUS  current
        DESCRIPTION
            "mtree RetentionLock Status"
        ::= { mtreeRetentionLockEntry 3 }

     mtreeRetentionLockUUID OBJECT-TYPE
        SYNTAX  DDMibTableString32TC
        MAX-ACCESS read-only 
        STATUS  current
        DESCRIPTION
            "mtree RetentionLock UUID"
        ::= { mtreeRetentionLockEntry 4 }

    mtreeRetentionLockMinRetentionPeriod OBJECT-TYPE
        SYNTAX  DDMibTableString32TC
        MAX-ACCESS  read-only 
        STATUS  current
        DESCRIPTION
            "mtree RetentionLock Minimum Retention Period"
        ::= { mtreeRetentionLockEntry 5 }

    mtreeRetentionLockMaxRetentionPeriod OBJECT-TYPE
        SYNTAX  DDMibTableString32TC
        MAX-ACCESS  read-only
        STATUS  current
        DESCRIPTION
            "mtree RetentionLock Maximum Retention Period"
        ::= { mtreeRetentionLockEntry 6 }

    
--
-- Common Notifications 
-- ====================
--
-- dataDomainMib        	(1.3.6.1.4.1.19746)
--  dataDomainMibNotifications	(1.3.6.1.4.1.19746.2)
--
-- **********************************************************************

dataDomainMibTraps OBJECT IDENTIFIER ::= { dataDomainMibNotifications 0 }

  powerSupplyFailedAlarm NOTIFICATION-TYPE
	STATUS	deprecated
        DESCRIPTION
            "Meaning: Power Supply failed
             What to do: replace the power supply"
        ::= { dataDomainMibTraps 1 } 

  systemOverheatWarningAlarm NOTIFICATION-TYPE
        OBJECTS { tempSensorDescription } 
	STATUS deprecated
	DESCRIPTION
	    "Meaning: the temperature reading of one of the thermometers in the Chassis  has exceeded 
	     the 'warning' temperature level.  If it continues to rise, it may eventually trigger a 
	     shutdown of the DDR.  The index value of the alarm indicates the thermometer index that
	     may be looked up in the environmentals table 'temperatures' for more information about
	     the actual thermometer reading the high value.
	     What to do: check the Fan status, temperatures of the environment in which the DDR is,
	     and other factors which may increase the temperature."
	::= { dataDomainMibTraps 2 }

  systemOverheatAlertAlarm NOTIFICATION-TYPE
        OBJECTS { tempSensorDescription } 
	STATUS deprecated
	DESCRIPTION
	    "Meaning: the temperature reading of one of the thermometers in the Chassis is more than
	     halfway between the 'warning' and 'shutdown' temperature levels.  If it continues to rise, 
	     it may eventually trigger a shutdown of the DDR.  The index value of the alarm indicates 
	     the thermometer index that may be looked up in the environmentals table 'temperatures' 
	     for more information about the actual thermometer reading the high value.
	     What to do: check the Fan status, temperatures of the environment in which the DDR is,
	     and other factors which may increase the system temperature."
	::= { dataDomainMibTraps 3 }

  systemOverheatShutdownAlarm NOTIFICATION-TYPE
        OBJECTS { tempSensorDescription } 
	STATUS deprecated
	DESCRIPTION
	    "Meaning: the temperature reading of one of the thermometers in the Chassis has reached
	     or exceeded the 'shutdown' temperature level. The DDR will be shutdown to prevent damage
	     to the system.  The index value of the alarm indicates the thermometer index that may be
	     looked up in the environmentals table 'temperatures' for more information about the actual 
	     thermometer reading the high value.
	     What to do: Once the system has been brought back up, after checking for high environment
	     temperatures or other factors which may increase the system temperature, check other 
	     environmental values, such as Fan Status, Disk Temperatures, etc..."
	::= { dataDomainMibTraps 4 }

  fanModuleFailedAlarm NOTIFICATION-TYPE
        OBJECTS { fanDescription } 
	STATUS	deprecated
        DESCRIPTION
            "Meaning: a Fan Module in the enclosure has failed.  The index of the fan is given
             as the index of the alarm.  This same index can be looked up in the environmentals
             table 'fanProperies' for more information about which fan has failed.
             What to do: replace the fan"
        ::= { dataDomainMibTraps 5 } 

  nvramFailingAlarm NOTIFICATION-TYPE
	STATUS	deprecated
        DESCRIPTION
            "Meaning: The system has detected that the NVRAM is potentially failing.  There has
            been an excessive amount of PCI or Memory errors. The nvram tables 'nvramProperties'
            and 'nvramStats' may provide for information on why the NVRAM is failing.
            What to do: check the status of the NVRAM after reboot, and replace if the
            errors continue."
        ::= { dataDomainMibTraps 6 } 

  fileSystemFailedAlarm NOTIFICATION-TYPE
	STATUS	deprecated
        DESCRIPTION
            "Meaning: The File System process on the DDR has had a serious problem and has had
             to restart.
             What to do: check the system logs for conditions that may be triggering the failure.
             Other alarms may also indicate why the File System is having problems."
        ::= { dataDomainMibTraps 7 } 

  fileSpaceMaintenanceAlarm NOTIFICATION-TYPE
        OBJECTS { fileSystemResourceName } 
	STATUS deprecated
	DESCRIPTION
	    "Meaning: DDVAR File System Resource Space is running low for system maintenance activities.  The
	     system may not have enough space for the routine system activities to run without error.
	     What to do: Delete unneeded files, such as old log files, support bundles, core files,
	     upgrade rpm files stored in the /ddvar file system."
	::= { dataDomainMibTraps 8 }

  fileSpacePreWarningAlarm NOTIFICATION-TYPE
        OBJECTS { fileSystemResourceName } 
	STATUS deprecated
	DESCRIPTION
	    "Meaning: A File System Resource space is 80-85% utilized.  While not critical, the space usage
	     should be monitored.  The index value of the alarm indicates the file system index that may be 
	     looked up in the fileSystem table 'fileSystemSpace' for more information about the actual FS 
	     that is getting full. 
	     What to do: no action is necessary, but the file system should be monitored more closely as it
	     grows more full.  Further alarms will be sent when and if the file system space is approaching very full."
	::= { dataDomainMibTraps 9 }

  fileSpaceWarningAlarm NOTIFICATION-TYPE
        OBJECTS { fileSystemResourceName } 
	STATUS deprecated
	DESCRIPTION
	    "Meaning: A File System Resource space is 90% utilized.  The index value of the alarm indicates 
	     the file system index that may be looked up in the fileSystem table 'fileSystemSpace' 
	     for more information about the actual FS that is getting full. 
	     What to do: Delete unneeded files, such as old log files, support bundles, core files,
	     upgrade rpm files stored in the /ddvar file system.  Consider upgrading the hardware or adding
	     shelves to high-end units.  Reducing the retention times for backup data can also help. When 
	     files are deleted from outside of the /ddvar space, filesys clean will have to be done before 
	     the space is recovered."
	::= { dataDomainMibTraps 10 }

  fileSpaceSevereAlarm NOTIFICATION-TYPE
        OBJECTS { fileSystemResourceName } 
	STATUS deprecated
	DESCRIPTION
	    "Meaning: A File System Resource space is 95% utilized.  The index value of the alarm indicates 
	     the file system index that may be looked up in the fileSystem table 'fileSystemSpace' 
	     for more information about the actual FS that is getting full. 
	     What to do: Delete unneeded files, such as old log files, support bundles, core files,
	     upgrade rpm files stored in the /ddvar file system.  Consider upgrading the hardware or adding
	     shelves to high-end units.  Reducing the retention times for backup data can also help. When 
	     files are deleted from outside of the /ddvar space, filesys clean will have to be done before 
	     the space is recovered."
	::= { dataDomainMibTraps 11 }

  fileSpaceCriticalAlarm NOTIFICATION-TYPE
        OBJECTS { fileSystemResourceName } 
	STATUS deprecated
	DESCRIPTION
	    "Meaning: A File System Resource space is 100% utilized.  The index value of the alarm indicates 
	     the file system index that may be looked up in the fileSystem table 'fileSystemSpace' 
	     for more information about the actual FS that is full. 
	     What to do: Delete unneeded files, such as old log files, support bundles, core files,
	     upgrade rpm files stored in the /ddvar file system.  Consider upgrading the hardware or adding
	     shelves to high-end units.  Reducing the retention times for backup data can also help. When 
	     files are deleted from outside of the /ddvar space, filesys clean will have to be done before 
	     the space is recovered."
	::= { dataDomainMibTraps 12 }

  diskFailedAlarm NOTIFICATION-TYPE
        OBJECTS { diskSerialNumber } 
	STATUS	deprecated
        DESCRIPTION
            "Meaning: some problem has been detected about the indicated disk.  The index value 
             of the alarm indicates the disk index that may be looked up in the disk tables 
             'diskProperties', 'diskPerformance', and 'diskReliability' for more information 
             about the actual disk that has failed.
             What to do: replace the disk."
        ::= { dataDomainMibTraps 14 } 

  diskOverheatWarningAlarm NOTIFICATION-TYPE
        OBJECTS { diskTemperature } 
	STATUS deprecated
	DESCRIPTION
	    "Meaning: the temperature reading of the indicated disk has exceeded the 'warning' 
	     temperature level.  If it continues to rise, it may eventually trigger a 
	     shutdown of the DDR.  The index value of the alarm indicates the disk index that
	     may be looked up in the disk tables 'diskProperties', 'diskPerformance', and 
	     'diskReliability' for more information about the actual disk reading the high value.
	     What to do: check the disk status, temperatures of the environment in which the DDR is,
	     and other factors which may increase the temperature."
	::= { dataDomainMibTraps 15 }

  diskOverheatAlertAlarm NOTIFICATION-TYPE
        OBJECTS { diskTemperature } 
	STATUS deprecated
	DESCRIPTION
	    "Meaning: the temperature reading of the indicated disk is more than halfway between
	     the 'warning' and 'shutdown' temperature levels. If it continues to rise, it will 
	     trigger a shutdown of the DDR.  The index value of the alarm indicates the disk index that
	     may be looked up in the disk tables 'diskProperties', 'diskPerformance', and 
	     'diskReliability' for more information about the actual disk reading the high value.
	     What to do: check the disk status, temperatures of the environment in which the DDR is,
	     and other factors which may increase the temperature.  If the temperature continues stays
	     at this level or rises, and no other disks are reading this trouble, consider 'failing'
	     the disk, and get a replacement."
	::= { dataDomainMibTraps 16 }

  diskOverheatShutdownAlarm NOTIFICATION-TYPE
        OBJECTS { diskTemperature } 
	STATUS deprecated
	DESCRIPTION
	    "Meaning: the temperature reading of the indicated disk has surpassed the 'shutdown' 
	     temperature level. The DDR will be shutdown.  The index value of the alarm indicates 
	     the disk index that may be looked up in the disk tables 'diskProperties', 'diskPerformance', 
	     and 'diskReliability' for more information about the actual disk reading the high value.
	     What to do: Boot the DDR and monitor the status and temperatures.  If the same disk has
	     continued problems, consider 'failing' it and get a replacement disk."
	::= { dataDomainMibTraps 17 }

  raidReconSevereAlarm NOTIFICATION-TYPE
	STATUS deprecated
	DESCRIPTION
	    "Meaning: A raid group is MAX degraded with no reconstruction after less than 71 hours or 
             A disk group is degraded with none max degraded with no reconstruction. This alarm is sent 
             every 1 hour until 71 hours after which raidReconCriticalAlarm or raidReconCriticalShutdown
             alarm is generated. This can happen due to a disk failing at run-time or boot-time.
	     What to do: while it is still possible that the reconstruction could succeed, the disk
	     should be replaced to ensure data safety."
	::= { dataDomainMibTraps 18 }

  raidReconCriticalAlarm NOTIFICATION-TYPE
	STATUS deprecated
	DESCRIPTION
	    "Meaning: Raid group is MAX degraded with no reconstruction after 71 hours. This can
	     happen due to a disk failing at run-time or boot-up.
	     What to do: the disk should be replaced to ensure data safety."
	::= { dataDomainMibTraps 19 }

  raidReconCriticalShutdownAlarm NOTIFICATION-TYPE
	STATUS deprecated
	DESCRIPTION
	    "Meaning: Raid group is MAX degraded with no reconstruction after 71 hours. This can
             happen due to a disk failing at run-time or boot-up.
	     What to do: the disk must be replaced."
	::= { dataDomainMibTraps 20 }

  raidGroupMissingAlarm NOTIFICATION-TYPE
	STATUS deprecated
	DESCRIPTION
	    "Meaning: one or more raid groups are missing.
	     What to do: disk may need replacement, or raid administration may be necessary."
	::= { dataDomainMibTraps 21 }

  diskNoSpareAlarm NOTIFICATION-TYPE
	STATUS deprecated
	DESCRIPTION
	    "Meaning: there is no spare available for the raid group.
	     What to do: disk may need replacement, or raid administration may be necessary."
	::= { dataDomainMibTraps 22 }

  diskPathAlarm NOTIFICATION-TYPE
        OBJECTS { diskSerialNumber } 
	STATUS deprecated
	DESCRIPTION
	    "Meaning: multipath configuration is experiencing a problem.  The number of paths set up is less than 
	    the required number of paths.  Disk index is the first disk in the enclosure with multipath.
	     What to do: multipath disk administration may be necessary."
	::= { dataDomainMibTraps 23 }

  diskSASAlarm NOTIFICATION-TYPE
	STATUS deprecated
	DESCRIPTION
	    "Meaning: SAS configuration error.  Maximum enclosures has been reached, or there
	    is a topology problem.
	     What to do: SAS configuration documentation should be consulted.  administration may be necessary."
	::= { dataDomainMibTraps 24 }

  diskSASHBAAlarm NOTIFICATION-TYPE
        OBJECTS { diskSerialNumber } 
	STATUS deprecated
	DESCRIPTION
	    "Meaning: Unsupported multi-path setting is enabled in the hba firmware.
	     What to do: contact Data Domain support."
	::= { dataDomainMibTraps 25 }

  snapshotFullAlarm NOTIFICATION-TYPE
	STATUS deprecated
	DESCRIPTION
	    "Meaning: maximum number of snapshots has been reached.
	     What to do: expire some old snapshots to make room."
	::= { dataDomainMibTraps 26 }

  snapshotHWMAlarm NOTIFICATION-TYPE
	STATUS deprecated
	DESCRIPTION
	    "Meaning: the number of snapshots has exceeded a predefined percentage (current 90%) of the maximum.
	     What to do: begin expiring snapshots so that the maximum is not reached."
	::= { dataDomainMibTraps 27 }

  clusterNodeAlarm NOTIFICATION-TYPE
	STATUS deprecated
	DESCRIPTION
	    "Meaning: node is not reachable on any network interface.
	     What to do: check status of network and wiring.  if that fails, try 
	     rebooting the node."
	::= { dataDomainMibTraps 28 }

  clusterInterfaceAlarm NOTIFICATION-TYPE
	STATUS deprecated
	DESCRIPTION
	    "Meaning: one interface of the cluster node is down.
	     What to do: check status of network and wiring.  if that fails, try 
	     rebooting the node."
	::= { dataDomainMibTraps 29 }

  replSyncAlarm NOTIFICATION-TYPE
  		OBJECTS { replStatus }
	STATUS deprecated
	DESCRIPTION
	    "Meaning: a replication context is disabled due to nvram loss.
	     What to do: break replication on source and destination, then reconfigure
	     them and run replication sync."
	::= { dataDomainMibTraps 30 }

  systemStartupAlarm NOTIFICATION-TYPE
	STATUS deprecated
	DESCRIPTION
	    "Meaning: system has rebooted or started.  this does not indicate any abnormal activity.
	     What to do: nothing, unless reboot was triggered by other abnormal conditions, such as
	     temperature, fan or power problems."
	::= { dataDomainMibTraps 31 }

  filesysRelaunchAlarm NOTIFICATION-TYPE
	STATUS deprecated
	DESCRIPTION
	    "Meaning: file system has undergone too many relaunches.  it is probably unstable.
	     What to do: consult system logs.  software or hardware restart may fix the malfunction."
	::= { dataDomainMibTraps 32 }

  filesysDDGCFailedAlarm NOTIFICATION-TYPE
	STATUS deprecated
	DESCRIPTION
	    "Meaning: DDGC cleaning process has failed.
	     What to do: consult system logs.  software or hardware restart may fix the malfunction."
	::= { dataDomainMibTraps 33 }

  filesysGeneralProblemAlarm NOTIFICATION-TYPE
	STATUS deprecated
	DESCRIPTION
	    "Meaning: a general problem has occurred with the file system.
	     What to do: consult system logs.  software or hardware restart may fix the malfunction."
	::= { dataDomainMibTraps 34 }
	
  diskUnsupportedAlarm NOTIFICATION-TYPE
        OBJECTS { diskSerialNumber } 
	STATUS	deprecated
        DESCRIPTION
            "Meaning: the model of the disk is unsupported by current DD platform.  The index value 
             of the alarm indicates the disk index that may be looked up in the disk tables 
             'diskProperties', 'diskPerformance', and 'diskReliability' for more information 
             about the actual disk.
             What to do: replace the disk."
        ::= { dataDomainMibTraps 35 }
 
  eventIPMIUnmanageAlarm NOTIFICATION-TYPE
	STATUS	deprecated
        DESCRIPTION
            "Meaning: IPMI unmanaged alert detected.
             What to do: check alert message"
        ::= { dataDomainMibTraps 36 } 

-- autogenerated notifications here
-- generated notifications
generatedNotificationsGroup NOTIFICATION-GROUP
NOTIFICATIONS {
   cpismissing,
   unknownDomainAlert,
   nT4DomainAlert,
   controllerUnreachableAlert,
   controllerIfaceUnreachableAlert,
   containerMarkedInvalid,
   correctableECCLimitReached,
   uncorrectableECCerror,
   legacyChassisTempWarning,
   legacyChassisTempCritical,
   legacyPowerSupplyWarning,
   legacyFanWarning,
   powerSupplyWarning,
   fanWarning,
   voltageWarning,
   powerWarning,
   correctECCWarning,
   nonThreshWarning,
   processorWarning,
   powerUnitWarning,
   unCorrectECCWarning,
   chassisSensorWarning,
   chassisSensorCritical,
   chassisTempWarning,
   chassisTempCritical,
   cPUFailureWarning,
   legacyBMCHangCritical,
   bMCHangCritical,
   abnormalShutdown,
   smiMrc,
   dimmTempWarning,
   dimmTempCritical,
   systemReset,
   tooManyRelaunches,
   filesystemProblem,
   dDGCFailedInShutdown,
   dDFSFailedInShutdown,
   dDFSNotCleanlyShutdown,
   dDGCFailed1,
   dDGCFailed2,
   dDFSNoHeartbeat,
   dDGCFailed3,
   dDFSDiedAfterReboot,
   dDFSDied,
   dDFSRebooted,
   dDFSRebootedDisabled,
   indexRebuildComplete,
   historicalDatabaseRecoverError,
   historicalDatabaseBackupError,
   historicalDatabaseUpgradeError,
   historicalDatabasePruneError,
   noHistoricalDatabaseError,
   hDTFileTransferFailed,
   hDTSystemError,
   dIMMFailureAlert,
   memoryAlert,
   portPathDisabled,
   diskPathRedundancy,
   missingPortConnection,
   missingLunPath,
   missingDiskPath,
   missingEnclosurePath,
   linkLoss,
   linkOscillations,
   linkConfiguration,
   linkUpAndRunningAlarm,
   nvramWarning,
   nvramBatteryAlert,
   nvramErrorAlert,
   nvramBoardTempAlert,
   nvramBoardVoltageAlert,
   nvramBatteryTempAlert,
   nvramBatteryVoltageAlert,
   nvramBatteryChargeAlert,
   nvramBatteryLowChargeAlert,
   nvramBatteryGaugeAlert,
   nvramBatteryDetectAlert,
   nvramBatteryChargeDisableAlert,
   nvramCorrectMemAlert,
   nvramUncorrectMemAlert,
   nvramPCIeAlert,
   nvramCPUAlert,
   nvramBatteryPowerDisableAlert,
   nvramReadOnlyAlert,
   nvramCardDetectAlert,
   nvramWrongModelAlert,
   nvramMemSizeAlert,
   nvramLinkSpeedAlert,
   nvramLinkWidthAlert,
   nvramGetInfoAlert,
   nvramTargetLinkSpeedAlert,
   nvramWrongCountAlert,
   nvramMixAlert,
   ext3NvlogDisabled,
   phyalert,
   replProgressThreshholdReached,
   replNeedResync,
   replLogFull,
   replIncompatibleWorm,
   replDestNotConfigured,
   replLagThreshholdReached,
   replPathTooLong,
   sASEnclosureCheck,
   sASTopologyCheck,
   sASPortDisabled,
   enclosureMixType,
   enclosureFwUpgradeAlert,
   sSLCertificateCorrupted,
   missingSysadminRegistryEntry,
   smsRestartFullQ,
   mailserverError,
   snapshotOver90Percent,
   snapshotLimitReached,
   sNTZMultipleIterations,
   coredumpWarning,
   coredumpDisabled,
   spaceOver80Percent,
   spaceOver90Percent,
   diskAccessError,
   diskFailure,
   diskTemperatureWarning,
   diskTemperatureShutdown,
   unsupportedHardwareSpareSize,
   missingDiskGroup,
   diskGroupReconstructionNoProgress,
   diskGroupReconstruction,
   diskGroupReconstructionShutdown,
   diskGroupReconstructionCritical,
   diskUnknown,
   enclUnknown,
   lowSpares,
   unsupportedConfigurationROL,
   syslogAlert,
   vTLFCLinkOffline,
   vTLFCLinkOscillations,
   vTLFCLinkOnline
}
STATUS  current
DESCRIPTION
   "A collection of objects providing  notifications, automatically generated by build."
::= { dataDomainMibGroups 5000 }

cpismissing NOTIFICATION-TYPE
STATUS current
   DESCRIPTION
   "Description: 
        One archive cp is missing
    
   Action: 
        - check power connection of each shelf.
        - check sas connection of each shelf.
    "
::= { dataDomainMibTraps 5500 }

unknownDomainAlert NOTIFICATION-TYPE
STATUS current
   DESCRIPTION
   "Description: 
            During upgrade the system could not determine whether it is joined into NT4 domain or
            Windows 2000 or newer AD domain.
        
   Action: 
            If the system is joined into an NT4 domain it is recommended to move (join) the system
            into Windows 2000 or newer AD domain. NT4 domain support is deprecated 
            and in a future release NT4 domains will not be supported.
            If the system is already joined into Windows 2000 or newer domain, 
            please switch the authentication mode.
            Contact your contracted support provider or visit us online at https://my.datadomain.com.
        "
::= { dataDomainMibTraps 5000 }

nT4DomainAlert NOTIFICATION-TYPE
STATUS current
   DESCRIPTION
   "Description: 
            During upgrade the system determined that it is joined into an NT4 domain.
        
   Action: 
            It is recommended to move (join) the system into Windows 2000 or newer AD domain since
            NT4 domain support is deprecated. 
            In a future release NT4 domains will not be supported.
        "
::= { dataDomainMibTraps 5001 }

controllerUnreachableAlert NOTIFICATION-TYPE
STATUS current
   DESCRIPTION
   "Description: 
        This is a GDA event raised by the Master controller when it fails to reach a Worker
        controller for more than 5 minutes. An unreachable Worker controller implies none of the Worker
        controller interfaces are pingable from the Master controller.
    
   Action: 
        Check the status of network interfaces on both controllers.
        Check network connectivity between the Master and Worker controller.
        Make sure all cables are securely connected.
    "
::= { dataDomainMibTraps 5002 }

controllerIfaceUnreachableAlert NOTIFICATION-TYPE
STATUS current
   DESCRIPTION
   "Description: 
        This is a GDA event raised by the Master controller when it fails to reach a particular
        Worker controller interface for more than 5 minutes. An unreachable interface implies that
        it is not pingable from its Master controller equivalent interface.
    
   Action: 
        Check network interface status on both controllers.
        Check network connectivity between the Master and Worker controller.
        Make sure all cables are securely connected.
    "
::= { dataDomainMibTraps 5003 }

containerMarkedInvalid NOTIFICATION-TYPE
STATUS current
   DESCRIPTION
   "Description: 
        The restorer has marked container %1 of set %3 invalid.  This usually
        indicates that the restorer cannot verify or scrub the container.
    
   Action: 
        Contact your contracted support provider or visit us online at https://my.datadomain.com.
    "
::= { dataDomainMibTraps 5501 }

correctableECCLimitReached NOTIFICATION-TYPE
STATUS current
   DESCRIPTION
   "Description: 
      Single bit correctable ECC limit reached.
    
   Action: 
      Replace the failed DIMM(s).
      Contact your contracted support provider or visit us online at https://my.datadomain.com.
    "
::= { dataDomainMibTraps 5004 }

uncorrectableECCerror NOTIFICATION-TYPE
STATUS current
   DESCRIPTION
   "Description: 
      Multi bit uncorrectable ECC error.
    
   Action: 
      Replace the failed DIMM(s).
      Contact your contracted support provider or visit us online at https://my.datadomain.com.
    "
::= { dataDomainMibTraps 5005 }

legacyChassisTempWarning NOTIFICATION-TYPE
   OBJECTS { tempSensorDescription }
STATUS current
   DESCRIPTION
   "Description: 
        Current temperature sensor reading exceeds warning threshold.
    
   Action: 
        Monitor temperature readings. If alert persists, check ambient room temperature 
        and for blocked air flow. 
        If the problem persists, contact your contracted support provider or visit us online at https://my.datadomain.com.
    "
::= { dataDomainMibTraps 5006 }

legacyChassisTempCritical NOTIFICATION-TYPE
   OBJECTS { tempSensorDescription }
STATUS current
   DESCRIPTION
   "Description: 
        Current temperature sensor reading exceeds critical threshold.
    
   Action: 
        Check ambient room temperature and for blocked air flow. 
        If the problem persists, contact your contracted support provider or visit us online at https://my.datadomain.com.
    "
::= { dataDomainMibTraps 5007 }

legacyPowerSupplyWarning NOTIFICATION-TYPE
   OBJECTS { powerModuleDescription }
STATUS current
   DESCRIPTION
   "Description: 
        A power supply has failed, is unplugged, or absent.
    
   Action: 
        Check power supply cables and LED. Replace with other working power supply.
        If the problem persists, contact your contracted support provider or visit us online at https://my.datadomain.com.
    "
::= { dataDomainMibTraps 5008 }

legacyFanWarning NOTIFICATION-TYPE
   OBJECTS { fanDescription }
STATUS current
   DESCRIPTION
   "Description: 
        A fan has failed.
    
   Action: 
        Check for any failed fan. If yes, replace with new fan.
        If the problem persists, contact your contracted support provider or visit us online at https://my.datadomain.com.
    "
::= { dataDomainMibTraps 5009 }

powerSupplyWarning NOTIFICATION-TYPE
   OBJECTS { powerModuleDescription }
STATUS current
   DESCRIPTION
   "Description: 
        A power supply has failed, is unplugged, or absent.
    
   Action: 
        Check power supply cables and LED. Replace with other working power supply.
        If the problem persists, contact your contracted support provider or visit us online at https://my.datadomain.com.
    "
::= { dataDomainMibTraps 5010 }

fanWarning NOTIFICATION-TYPE
   OBJECTS { fanDescription }
STATUS current
   DESCRIPTION
   "Description: 
        A fan has failed or is missing.
    
   Action: 
        Check for any failed or missing fan. Reseat the fan.
        If the problem persists, contact your contracted support provider or visit us online at https://my.datadomain.com.
    "
::= { dataDomainMibTraps 5011 }

voltageWarning NOTIFICATION-TYPE
STATUS current
   DESCRIPTION
   "Description: 
        Voltage sensor reading exceeds warning threshold.
    
   Action: 
        If the problem persists, contact your contracted support provider or visit us online at https://my.datadomain.com.
    "
::= { dataDomainMibTraps 5012 }

powerWarning NOTIFICATION-TYPE
STATUS current
   DESCRIPTION
   "Description: 
        Current power consumption reading exceeds warning threshold.
    
   Action: 
        If the problem persists, contact your contracted support provider or visit us online at https://my.datadomain.com.
    "
::= { dataDomainMibTraps 5013 }

correctECCWarning NOTIFICATION-TYPE
STATUS current
   DESCRIPTION
   "Description: 
        Memory correctable ECC errors exceed warning threshold.
    
   Action: 
        These memory errors are automatically corrected by the system. 
        If the problem persists, contact your contracted support provider or visit us online at https://my.datadomain.com.
    "
::= { dataDomainMibTraps 5014 }

nonThreshWarning NOTIFICATION-TYPE
STATUS current
   DESCRIPTION
   "Description: 
        Current non-threshold type sensor reading exceeds warning threshold.
    
   Action: 
        Check specific alert message for appropriate action.
        If the problem persists, contact your contracted support provider or visit us online at https://my.datadomain.com.
    "
::= { dataDomainMibTraps 5015 }

processorWarning NOTIFICATION-TYPE
STATUS current
   DESCRIPTION
   "Description: 
        Processor thermal sensor alert.
    
   Action: 
        If the problem persists, contact your contracted support provider or visit us online at https://my.datadomain.com.
    "
::= { dataDomainMibTraps 5016 }

powerUnitWarning NOTIFICATION-TYPE
STATUS current
   DESCRIPTION
   "Description: 
        Power unit status alert (power off, power cycle, AC lost, power unit failure detected, etc.).
    
   Action: 
        This alert is expected after power off, power cycle, or lost of AC (main power) event.
        If this alert is not expected, check power cords or AC (main).
        If the problem persists, contact your contracted support provider or visit us online at https://my.datadomain.com.
    "
::= { dataDomainMibTraps 5017 }

unCorrectECCWarning NOTIFICATION-TYPE
STATUS current
   DESCRIPTION
   "Description: 
        Memory uncorrectable ECC error alert.
    
   Action: 
        If the problem persists, contact your contracted support provider or visit us online at https://my.datadomain.com.
    "
::= { dataDomainMibTraps 5018 }

chassisSensorWarning NOTIFICATION-TYPE
STATUS current
   DESCRIPTION
   "Description: 
        Other chassis sensor alert.
    
   Action: 
        Check specific alert message for information.
        If the problem persists, contact your contracted support provider or visit us online at https://my.datadomain.com.
    "
::= { dataDomainMibTraps 5019 }

chassisSensorCritical NOTIFICATION-TYPE
STATUS current
   DESCRIPTION
   "Description: 
        Current sensor reading or state exceeds critical condition.
    
   Action: 
        Check the specific alert message for information.
        Monitor temperature readings. If alert persists, check ambient room temperature 
        and for blocked air flow. 
        If the problem persists, contact your contracted support provider or visit us online at https://my.datadomain.com.
    "
::= { dataDomainMibTraps 5020 }

chassisTempWarning NOTIFICATION-TYPE
   OBJECTS { tempSensorDescription }
STATUS current
   DESCRIPTION
   "Description: 
        Current temperature sensor reading exceeds warning threshold.
    
   Action: 
        Monitor temperature readings. If alert persists, check ambient room temperature 
        and for blocked air flow. 
        If the problem persists, contact your contracted support provider or visit us online at https://my.datadomain.com.
    "
::= { dataDomainMibTraps 5021 }

chassisTempCritical NOTIFICATION-TYPE
   OBJECTS { tempSensorDescription }
STATUS current
   DESCRIPTION
   "Description: 
        Current temperature sensor reading exceeds critical threshold.
    
   Action: 
        Check ambient room temperature and for blocked air flow. 
        If the problem persists, contact your contracted support provider or visit us online at https://my.datadomain.com.
    "
::= { dataDomainMibTraps 5022 }

cPUFailureWarning NOTIFICATION-TYPE
STATUS current
   DESCRIPTION
   "Description: 
        A CPU fault was detected.
    
   Action: 
        This might due to CPU hardware failure. 
        Check the log if this CPU is really bad. If yes, might need to do a chassis swap. 
        If the problem persists, contact your contracted support provider or visit us online at https://my.datadomain.com.
    "
::= { dataDomainMibTraps 5023 }

legacyBMCHangCritical NOTIFICATION-TYPE
STATUS current
   DESCRIPTION
   "Description: 
        BMC hang.
    
   Action: 
        Gracefully shut down the system and pull out all power cables to reset BMC. 
        Wait until all LEDS are off, reinsert the power cables, and press the power button 
        to turn on the system. 
    "
::= { dataDomainMibTraps 5024 }

bMCHangCritical NOTIFICATION-TYPE
STATUS current
   DESCRIPTION
   "Description: 
        BMC hang.
    
   Action: 
        If the alert has stayed for a while, check if environment CLIs also fails.
        If yes, gracefully shut down the system and pull out all power cables to reset BMC. 
        Wait until all LEDS are off. Reinsert the power cables, and press the power button 
        to turn on the system. 
    "
::= { dataDomainMibTraps 5025 }

abnormalShutdown NOTIFICATION-TYPE
STATUS current
   DESCRIPTION
   "Description: 
        The system has been shutdown by abnormal method, i.e. not by one of the following: 
        1) Via IPMI chassis control command 
        2) Via power button
        3) Via OS shutdown
    
   Action: 
        This alert is expected after lost of AC (main power) event.
        If this shutdown is not expected and persists, contact your contracted support provider or visit us online at https://my.datadomain.com.
    "
::= { dataDomainMibTraps 5026 }

smiMrc NOTIFICATION-TYPE
STATUS current
   DESCRIPTION
   "Description: 
        BIOS SMI MRC interrupt
    
   Action: 
        Check if system memory size has been decreased due to a DIMM has been disabled.
        If yes, replace the bad DIMM.
        If the problem persists, contact your contracted support provider or visit us online at https://my.datadomain.com.
    "
::= { dataDomainMibTraps 5502 }

dimmTempWarning NOTIFICATION-TYPE
STATUS current
   DESCRIPTION
   "Description: 
        Current DIMM temperature sensor reading exceeds warning threshold.
    
   Action: 
        Monitor temperature readings. If alert persists, check ambient room temperature 
        and for blocked air flow. 
        If the problem persists, contact your contracted support provider or visit us online at https://my.datadomain.com.
    "
::= { dataDomainMibTraps 5532 }

dimmTempCritical NOTIFICATION-TYPE
STATUS current
   DESCRIPTION
   "Description: 
        Current temperature sensor reading exceeds critical threshold.
    
   Action: 
        Check ambient room temperature and for blocked air flow. 
        If the problem persists, contact your contracted support provider or visit us online at https://my.datadomain.com.
    "
::= { dataDomainMibTraps 5533 }

systemReset NOTIFICATION-TYPE
STATUS current
   DESCRIPTION
   "Description: 
        A critical failure caused the system to unexpectedly shut down.
        The system was able to boot successfully either because the fault was corrected, the fault was transient, or the system was able to boot without the component causing the fault.
    
   Action: 
        Review the system for earlier alerts to determine the cause of the unexpected shut down.
        Check the system inventory to verify all components are configured as expected. 
        If this alert is issued again, contact your contracted support provider or visit us online at https://my.datadomain.com
    "
::= { dataDomainMibTraps 6529 }

tooManyRelaunches NOTIFICATION-TYPE
STATUS current
   DESCRIPTION
   "Description: 
    The filesystem process has failed to restart multiple times.
    
   Action: 
    Contact your contracted support provider or visit us online at https://my.datadomain.com.  The log files will indicate the true cause 
    for the failure and will provide guidance for a corrective action.
    "
::= { dataDomainMibTraps 5027 }

filesystemProblem NOTIFICATION-TYPE
STATUS current
   DESCRIPTION
   "Description: 
    A problem is preventing the filesystem from running. This usually 
    involves the storage being unavailable.
    
   Action: 
    Check disk shelf cabling.
    "
::= { dataDomainMibTraps 5028 }

dDGCFailedInShutdown NOTIFICATION-TYPE
STATUS current
   DESCRIPTION
   "Description: 
    DDGC process failed during shutdown.
    
   Action: 
    No action required.
    "
::= { dataDomainMibTraps 5029 }

dDFSFailedInShutdown NOTIFICATION-TYPE
STATUS current
   DESCRIPTION
   "Description: 
    The filesystem failed to shutdown cleanly. This can leave dirty data in 
    NVRAM when it would normally be flushed to disk. An unclean shutdown state 
    can prevent certain actions from being performed (i.e. upgrade).
    
   Action: 
    Re-enable the filesystem and try shutting it down again. The condition is 
    cleared if the second shutdown completes cleanly.
    "
::= { dataDomainMibTraps 5030 }

dDFSNotCleanlyShutdown NOTIFICATION-TYPE
STATUS current
   DESCRIPTION
   "Description: 
    DDFS didn't shutdown cleanly because of DDGC.
    
   Action: 
    No action required.
    "
::= { dataDomainMibTraps 5031 }

dDGCFailed1 NOTIFICATION-TYPE
STATUS current
   DESCRIPTION
   "Description: 
    DDGC process failed; restarting DDFS
    
   Action: 
    No action required.
    "
::= { dataDomainMibTraps 5032 }

dDGCFailed2 NOTIFICATION-TYPE
STATUS current
   DESCRIPTION
   "Description: 
    DDGC process failed; system disabled
    
   Action: 
    No action required.
    "
::= { dataDomainMibTraps 5033 }

dDFSNoHeartbeat NOTIFICATION-TYPE
STATUS current
   DESCRIPTION
   "Description: 
    Filesystem hung and failed to respond to heartbeats. 
    The filesystem has been restarted.
    
   Action: 
    Contact your contracted support provider or visit us online at https://my.datadomain.com for diagnosis of the cause of failure. 
    No other action required if filesystem successfully restarts.
    "
::= { dataDomainMibTraps 5034 }

dDGCFailed3 NOTIFICATION-TYPE
STATUS current
   DESCRIPTION
   "Description: 
    DDGC process failed during shutdown; starting DDFS.
    
   Action: 
    No action required.
    "
::= { dataDomainMibTraps 5035 }

dDFSDiedAfterReboot NOTIFICATION-TYPE
STATUS current
   DESCRIPTION
   "Description: 
    The filesystem failed to startup immediately after system reboot.
    
   Action: 
    Contact your contracted support provider or visit us online at https://my.datadomain.com for diagnosis of the cause of failure. No other 
    action required if filesystem successfully restarts.
    "
::= { dataDomainMibTraps 5036 }

dDFSDied NOTIFICATION-TYPE
STATUS current
   DESCRIPTION
   "Description: 
    The filesystem process failed and is restarting.
    
   Action: 
    Contact your contracted support provider or visit us online at https://my.datadomain.com for diagnosis of the cause of failure. No other 
    action required if filesystem successfully restarts.
    "
::= { dataDomainMibTraps 5037 }

dDFSRebooted NOTIFICATION-TYPE
STATUS current
   DESCRIPTION
   "Description: 
    This is just a notification alert that the system has been rebooted.
    
   Action: 
    No action required.
    "
::= { dataDomainMibTraps 5038 }

dDFSRebootedDisabled NOTIFICATION-TYPE
STATUS current
   DESCRIPTION
   "Description: 
    This is a notification alert sent out during system startup following a 
    reboot. The system is rebooted with the filesystem in disabled state.
    
   Action: 
    No action is required unless the intent is to have the filesystem enabled. 
    In that case, invoke the 'filesys enable' command.
    "
::= { dataDomainMibTraps 5039 }

indexRebuildComplete NOTIFICATION-TYPE
STATUS current
   DESCRIPTION
   "Description: 
        Index rebuild completed.
    
   Action: 
        Informational.
    "
::= { dataDomainMibTraps 5040 }

historicalDatabaseRecoverError NOTIFICATION-TYPE
STATUS current
   DESCRIPTION
   "Description: 
        Historical database recovery failed. All existing historical data has been lost.
        Data in the historical database is used for some system reports, but it is not
        required for proper system functioning.  This failure may occur during head
        swap processing if recovery to create the new head primary historical database
        from the shelf database files fails.
        The system successfully created a new historical database.
    
   Action: 
        Contact your contracted support provider or visit us online at https://my.datadomain.com
        to debug this problem and possibly attempt recovery of the lost historical data.
    "
::= { dataDomainMibTraps 5041 }

historicalDatabaseBackupError NOTIFICATION-TYPE
STATUS current
   DESCRIPTION
   "Description: 
        Historical database backup failed. If the primary historical database fails
        without a recent backup present, some or all of the historical data can be
        lost when the primary historical database is restored from its backup and log
        files.
        Data in the historical database is used for some system reports, but it is
        not required for proper system functioning.
    
   Action: 
        If this alert is issued 2 days in a row, contact your contracted support provider or visit us online at https://my.datadomain.com to help debug the problem.
    "
::= { dataDomainMibTraps 5042 }

historicalDatabaseUpgradeError NOTIFICATION-TYPE
STATUS current
   DESCRIPTION
   "Description: 
            Historical database upgrade failed during software upgrade.  New historical
            data fields will not be saved.  Some UI reports might be unavailable, or
            be missing data. Otherwise, this should not affect the system.
        
   Action: 
            Contact your contracted support provider or visit us online at https://my.datadomain.com to help debug the problem and upgrade the
            historical database.
        "
::= { dataDomainMibTraps 5043 }

historicalDatabasePruneError NOTIFICATION-TYPE
STATUS current
   DESCRIPTION
   "Description: 
            Historical database pruning failed.  Pruning ensures the historical database
            does not consume more than its allocated disk space.
        
   Action: 
            If this alert is issued 2 days in a row, contact your contracted support provider or visit us online at https://my.datadomain.com
            to help debug the problem. 
        "
::= { dataDomainMibTraps 5044 }

noHistoricalDatabaseError NOTIFICATION-TYPE
STATUS current
   DESCRIPTION
   "Description: 
        Historical database recovery failed. All existing historical data has been lost.
        Data in the historical database is used for some system reports, but it is not
        required for proper system functioning.  This failure may occur during head
        swap processing if recovery to create the new head primary historical database
        from the shelf database files fails.
        The system is running without historical database after failing to create a new one.
    
   Action: 
        Contact your contracted support provider or visit us online at https://my.datadomain.com
        to debug this problem and possibly attempt recovery of the lost historical data.
    "
::= { dataDomainMibTraps 5045 }

hDTFileTransferFailed NOTIFICATION-TYPE
STATUS current
   DESCRIPTION
   "Description: 
		Unable to send historical data update file to DDMS.
    
   Action: 
		Check network connection and permissions between the DDMS and this DDR.
		If the problem persists, contact your contracted support provider or visit us online at https://my.datadomain.com.
    "
::= { dataDomainMibTraps 5046 }

hDTSystemError NOTIFICATION-TYPE
STATUS current
   DESCRIPTION
   "Description: 
		System Error occurred while sending historical data to DDMS.
    
   Action: 
		Check configuration and system status, messages logs for indicative problems.
		If the problem persists, contact your contracted support provider or visit us online at https://my.datadomain.com.
    "
::= { dataDomainMibTraps 5047 }

dIMMFailureAlert NOTIFICATION-TYPE
STATUS current
   DESCRIPTION
   "Description: 
            DIMM failure detected. DDFS can't be enabled.
        
   Action: 
            Replace the bad DIMMS.
        "
::= { dataDomainMibTraps 5048 }

memoryAlert NOTIFICATION-TYPE
STATUS current
   DESCRIPTION
   "Description: 
            Current memory is less than configured. DDFS can't be enabled.
        
   Action: 
            Check the DIMMS in DDR. Add new DIMMS and/or replace the bad DIMMS.
        "
::= { dataDomainMibTraps 5049 }

portPathDisabled NOTIFICATION-TYPE
STATUS current
   DESCRIPTION
   "Description: 
        The user has forgotten to enable the path.
        There might be issues with failover if that path is not enabled.
    
   Action: 
        Enabling the path will resolve the issue.
    "
::= { dataDomainMibTraps 5050 }

diskPathRedundancy NOTIFICATION-TYPE
STATUS current
   DESCRIPTION
   "Description: 
        Only one path is seen on a multipath configuration and only one HBA is connected.
    
   Action: 
        Verify all storage cabling is connected correctly.
        Verify that HBA controllers are functional.
    "
::= { dataDomainMibTraps 5051 }

missingPortConnection NOTIFICATION-TYPE
STATUS current
   DESCRIPTION
   "Description: 
        A port and the attached storage has disappeared.
    
   Action: 
        Verify the connection and any external storage connected to the missing port.
    "
::= { dataDomainMibTraps 5052 }

missingLunPath NOTIFICATION-TYPE
STATUS current
   DESCRIPTION
   "Description: 
        The number of active paths to a LUN has changed.
    
   Action: 
        If this is due to reconfiguration, verify the topology and disable then re-enable
        multipath monitoring to reset the monitoring. If not, verify the storage cabling and that
        all paths are connected.
    "
::= { dataDomainMibTraps 5053 }

missingDiskPath NOTIFICATION-TYPE
   OBJECTS { diskSerialNumber }
STATUS current
   DESCRIPTION
   "Description: 
        The number of active paths to a disk has changed.
    
   Action: 
        If this is due to reconfiguration, verify the topology and disable then re-enable
        multipath monitoring to reset the monitoring. If not, verify the storage cabling and that
        all paths are connected.
    "
::= { dataDomainMibTraps 5054 }

missingEnclosurePath NOTIFICATION-TYPE
STATUS current
   DESCRIPTION
   "Description: 
        The number of active paths to an enclosure has changed.
    
   Action: 
        If this is due to reconfiguration, verify the topology and disable then re-enable
        multipath monitoring to reset the monitoring. If not, verify the storage cabling and that
        all paths are connected.
    "
::= { dataDomainMibTraps 5055 }

linkLoss NOTIFICATION-TYPE
   OBJECTS { ifIndex }
STATUS current
   DESCRIPTION
   "Description: 
        Link loss detected. 
    
   Action: 
        Check network connectivity.
    "
::= { dataDomainMibTraps 5056 }

linkOscillations NOTIFICATION-TYPE
   OBJECTS { ifIndex }
STATUS current
   DESCRIPTION
   "Description: 
        Link oscillations detected.
    
   Action: 
        Check network connectivity.
    "
::= { dataDomainMibTraps 5057 }

linkConfiguration NOTIFICATION-TYPE
   OBJECTS { ifIndex }
STATUS current
   DESCRIPTION
   "Description: 
        Link configuration problem detected.
    
   Action: 
        Check network configuration.
    "
::= { dataDomainMibTraps 5058 }

linkUpAndRunningAlarm NOTIFICATION-TYPE
   OBJECTS { ifIndex }
STATUS current
   DESCRIPTION
   "Description: 
        Link is up and running for a period of time after experiencing instability.
    
   Action: 
        No action needed.
    "
::= { dataDomainMibTraps 5098 }

nvramWarning NOTIFICATION-TYPE
STATUS current
   DESCRIPTION
   "Description: 
			DDFS is disabled due to a problem with an NVRAM card.
        
   Action: 
			Run CLI command 'alerts show current' to check for other NVRAM-related alerts,
			then follow troubleshooting steps to clear the alerts found. Contact your contracted support provider or visit us online at https://my.datadomain.com
        "
::= { dataDomainMibTraps 5059 }

nvramBatteryAlert NOTIFICATION-TYPE
   OBJECTS { nvramBatteryStatus }
STATUS current
   DESCRIPTION
   "Description: 
		DD OS detected an NVRAM card Battery Unit hardware fault.
		Probable causes:  1) Battery charging is disabled, or  2) One or more batteries is not charging.
    
   Action: 
		Run CLI command 'system show nvram' to check battery status.
		If the problem persists,   contact your contracted support provider or visit us online at https://my.datadomain.com.
    "
::= { dataDomainMibTraps 5060 }

nvramErrorAlert NOTIFICATION-TYPE
STATUS current
   DESCRIPTION
   "Description: 
		DD OS detected an NVRAM card fault.
		Probable cause: Excessive correctable errors exceed the warning threshold number.
    
   Action: 
        The NVRAM card may need to be replaced.
        Contact your contracted support provider or visit us online at https://my.datadomain.com.
    "
::= { dataDomainMibTraps 5061 }

nvramBoardTempAlert NOTIFICATION-TYPE
STATUS current
   DESCRIPTION
   "Description: 
		Current NVRAM board temperature sensor reading exceeds warning threshold temperature.
    
   Action: 
		Check if there is a system fan alert. If yes, replace with new fan. 
        Check ambient room temperature and for blocked air flow. 
        If the problem persists,contact your contracted support provider or visit us online at https://my.datadomain.com.
    "
::= { dataDomainMibTraps 5503 }

nvramBoardVoltageAlert NOTIFICATION-TYPE
STATUS current
   DESCRIPTION
   "Description: 
		DD OS detected an NVRAM board voltage sensor reading that exceeds the warning threshold voltage.
    
   Action: 
        Contact your contracted support provider or visit us online at https://my.datadomain.com.
    "
::= { dataDomainMibTraps 5504 }

nvramBatteryTempAlert NOTIFICATION-TYPE
STATUS current
   DESCRIPTION
   "Description: 
		DD OS detected an NVRAM battery temperature sensor reading that exceeds the warning threshold.
		Probable cause(s):  1) Insufficient air inflow, or  2) High system ambient temperature, or  3) Degraded batteries.
    
   Action: 
		Check if there is a system fan alert. If yes, replace with new fan. 
        If the problem persists, contact your contracted support provider or visit us online at https://my.datadomain.com.
    "
::= { dataDomainMibTraps 5505 }

nvramBatteryVoltageAlert NOTIFICATION-TYPE
STATUS current
   DESCRIPTION
   "Description: 
		DD OS detected an NVRAM battery voltage sensor reading that exceeds the warning threshold.
		Probable cause:  NVRAM battery unit is faulty.
    
   Action: 
		The NVRAM card Battery Unit may need to be replaced.
        Contact your contracted support provider or visit us online at https://my.datadomain.com.
    "
::= { dataDomainMibTraps 5506 }

nvramBatteryChargeAlert NOTIFICATION-TYPE
STATUS current
   DESCRIPTION
   "Description: 
		DD OS detected an NVRAM card Battery Unit hardware fault.
		Probable cause:  One or more batteries is not charging.
    
   Action: 
		Run CLI command 'system show nvram' to check battery status.
		If the problem persists,   contact your contracted support provider or visit us online at https://my.datadomain.com.
    "
::= { dataDomainMibTraps 5507 }

nvramBatteryLowChargeAlert NOTIFICATION-TYPE
STATUS current
   DESCRIPTION
   "Description: 
        NVRAM battery charge is lower than 80%.
    
   Action: 
        This alert will be cleared when battery charge is greater than or equal 80%.
        If the problem persists, contact your contracted support provider or visit us online at https://my.datadomain.com.
    "
::= { dataDomainMibTraps 5508 }

nvramBatteryGaugeAlert NOTIFICATION-TYPE
STATUS current
   DESCRIPTION
   "Description: 
		DD OS detected an NVRAM card Battery Unit hardware fault.
		Probable cause:  Battery Unit hardware is not accessible.
    
   Action: 
		contact your contracted support provider or visit us online at https://my.datadomain.com
    "
::= { dataDomainMibTraps 5509 }

nvramBatteryDetectAlert NOTIFICATION-TYPE
STATUS current
   DESCRIPTION
   "Description: 
		DD OS detected an NVRAM card Battery Unit hardware fault.
		Probable cause:  One or more batteries is missing.
    
   Action: 
		contact your contracted support provider or visit us online at https://my.datadomain.com
    "
::= { dataDomainMibTraps 5510 }

nvramBatteryChargeDisableAlert NOTIFICATION-TYPE
STATUS current
   DESCRIPTION
   "Description: 
		DD OS detected that NVRAM battery charging is disabled.
		Probable cause(s):  Battery charging disabled manually.
    
   Action: 
        Contact your contracted support provider or visit us online at https://my.datadomain.com.
    "
::= { dataDomainMibTraps 5511 }

nvramCorrectMemAlert NOTIFICATION-TYPE
STATUS current
   DESCRIPTION
   "Description: 
		DD OS detected an NVRAM card fault.
		Probable cause: NVRAM card correctable memory errors exceed the warning threshold number.
    
   Action: 
        The NVRAM card may need to be replaced.Contact your contracted support provider or visit us online at https://my.datadomain.com.
    "
::= { dataDomainMibTraps 5512 }

nvramUncorrectMemAlert NOTIFICATION-TYPE
STATUS current
   DESCRIPTION
   "Description: 
		DD OS detected an NVRAM card fault.
		Probable cause: NVRAM card has uncorrectable memory errors.
    
   Action: 
        The NVRAM card may need to be replaced.Contact your contracted support provider or visit us online at https://my.datadomain.com.
    "
::= { dataDomainMibTraps 5513 }

nvramPCIeAlert NOTIFICATION-TYPE
STATUS current
   DESCRIPTION
   "Description: 
		DD OS detected an NVRAM card fault.
		Probable cause: NVRAM card PCIe  errors.
    
   Action: 
        The NVRAM card may need to be replaced.Contact your contracted support provider or visit us online at https://my.datadomain.com.
    "
::= { dataDomainMibTraps 5514 }

nvramCPUAlert NOTIFICATION-TYPE
STATUS current
   DESCRIPTION
   "Description: 
		DD OS detected an NVRAM card fault.
		Probable cause: NVRAM card CPU errors.
    
   Action: 
		The NVRAM card may need to be replaced.Contact your contracted support provider or visit us online at https://my.datadomain.com.
    "
::= { dataDomainMibTraps 5515 }

nvramBatteryPowerDisableAlert NOTIFICATION-TYPE
STATUS current
   DESCRIPTION
   "Description: 
		DD OS detected that NVRAM battery power is disabled. 
    
   Action: 
        If the problem persists, contact your contracted support provider or visit us online at https://my.datadomain.com.
    "
::= { dataDomainMibTraps 5516 }

nvramReadOnlyAlert NOTIFICATION-TYPE
STATUS current
   DESCRIPTION
   "Description: 
		DD OS detected an NVRAM card Battery Unit hardware fault.
		Probable cause:  NVRAM card initialization error.
    
   Action:  
        If the problem persists, contact your contracted support provider or visit us online at https://my.datadomain.com.
    "
::= { dataDomainMibTraps 5517 }

nvramCardDetectAlert NOTIFICATION-TYPE
STATUS current
   DESCRIPTION
   "Description: 
        DD OS could not detect any NVRAM card(s) in the system.
		Probable causes:1) NVRAM card(s) may be absent or 
					 	2)NVRAM card(s) may not be seated properly.
    
   Action: 
        1)Check that the NVRAM card is properly seated. 
        2)contact your contracted support provider or visit us online at https://my.datadomain.com to get a new NVRAM card.
    "
::= { dataDomainMibTraps 5518 }

nvramWrongModelAlert NOTIFICATION-TYPE
STATUS current
   DESCRIPTION
   "Description: 
        DD OS detected an incompatible NVRAM card configuration.
		Probable cause:  NVRAM card in the system is not supported by DD OS version.
    
   Action: 
		The NVRAM card may need to be replaced.Contact your contracted support provider or visit us online at https://my.datadomain.com.
    "
::= { dataDomainMibTraps 5519 }

nvramMemSizeAlert NOTIFICATION-TYPE
STATUS current
   DESCRIPTION
   "Description: 
		DD OS detected an incompatible NVRAM card configuration.
		Probable cause:  Incompatible NVRAM card in the system.
    
   Action: 
		The NVRAM card may need to be replaced.Contact your contracted support provider or visit us online at https://my.datadomain.com.
    "
::= { dataDomainMibTraps 5520 }

nvramLinkSpeedAlert NOTIFICATION-TYPE
STATUS current
   DESCRIPTION
   "Description: 
		DD OS detected an incompatible NVRAM card configuration.
		Probable cause:  Incompatible NVRAM card in the system.
    
   Action: 
		The NVRAM card may need to be replaced.Contact your contracted support provider or visit us online at https://my.datadomain.com.
    "
::= { dataDomainMibTraps 5521 }

nvramLinkWidthAlert NOTIFICATION-TYPE
STATUS current
   DESCRIPTION
   "Description: 
		DD OS detected an incompatible NVRAM card configuration.
		Probable cause:  Incompatible NVRAM card in the system.
    
   Action: 
		The NVRAM card may need to be replaced.Contact your contracted support provider or visit us online at https://my.datadomain.com.
    "
::= { dataDomainMibTraps 5522 }

nvramGetInfoAlert NOTIFICATION-TYPE
STATUS current
   DESCRIPTION
   "Description: 
		DD OS detected an NVRAM card Battery Unit hardware fault.
		Probable cause:  Battery Unit hardware is not accessible.
    
   Action: 
        If the problem persists, contact your contracted support provider or visit us online at https://my.datadomain.com.
    "
::= { dataDomainMibTraps 5523 }

nvramTargetLinkSpeedAlert NOTIFICATION-TYPE
STATUS current
   DESCRIPTION
   "Description: 
		DD OS detected an incompatible NVRAM card configuration.
		Probable cause:  Incompatible NVRAM card in the system.
    
   Action: 
		The NVRAM card may need to be replaced.Contact your contracted support provider or visit us online at https://my.datadomain.com.
    "
::= { dataDomainMibTraps 5524 }

nvramWrongCountAlert NOTIFICATION-TYPE
STATUS current
   DESCRIPTION
   "Description: 
		DD OS detected an incompatible NVRAM card configuration.
		Probable cause:  The number of NVRAM cards in the system  is different from what DD OS expects.
    
   Action: 
		NVRAM card(s) may need  to be removed or added.Contact your contracted support provider or visit us online at https://my.datadomain.com.
    "
::= { dataDomainMibTraps 5525 }

nvramMixAlert NOTIFICATION-TYPE
STATUS current
   DESCRIPTION
   "Description: 
		DD OS detected an incompatible NVRAM card configuration.
		Probable cause:  Two different generations of NVRAM cards are in the system.
    
   Action: 
		The NVRAM card may need to be replaced.Contact your contracted support provider or visit us online at https://my.datadomain.com.
    "
::= { dataDomainMibTraps 5526 }

ext3NvlogDisabled NOTIFICATION-TYPE
STATUS current
   DESCRIPTION
   "Description: 
			NVRAM battery status is not OK to enable nvlog in this disk group.
			When battery status is OK, nvlog is enabled and this alert is cleared.
        
   Action: 
			Wait for NVRAM alert to be cleared. If the problem persists, contact your contracted support provider or visit us online at https://my.datadomain.com
        "
::= { dataDomainMibTraps 5527 }

phyalert NOTIFICATION-TYPE
STATUS current
   DESCRIPTION
   "Description: 
        Enclosure slot has been disabled.
    
   Action: 
        Replace the drive and enable the slot using CLI.
    "
::= { dataDomainMibTraps 5062 }

replProgressThreshholdReached NOTIFICATION-TYPE
   OBJECTS { replStatus }
STATUS current
   DESCRIPTION
   "Description: 
       Replication has not made progress recently
    
   Action: 
        - check the network
        - check the replica filesystem
        - check the 'replication status' or the GUI for errors
        - check the messages file for more specific messages
    "
::= { dataDomainMibTraps 5063 }

replNeedResync NOTIFICATION-TYPE
   OBJECTS { replStatus }
STATUS current
   DESCRIPTION
   "Description: 
        Replication needs resync. This context is disabled due to nvram loss.
    
   Action: 
        Please break replication on both source and destination, then
        reconfigure them and run replication resync.
    "
::= { dataDomainMibTraps 5064 }

replLogFull NOTIFICATION-TYPE
STATUS current
   DESCRIPTION
   "Description: 
        Number of free replication log entries is below threshold! Disabling write access.
    
   Action: 
        Allow configured contexts to make progress.  If a context
        is disabled, it should be re-enabled and allowed to progress.
        Any disabled contexts that are no longer needed should be broken
        using the replication break command.
    "
::= { dataDomainMibTraps 5065 }

replIncompatibleWorm NOTIFICATION-TYPE
STATUS current
   DESCRIPTION
   "Description: 
       Incompatible retention-locked files detected in resync
    
   Action: 
       Resync cannot be done with conflicting retention-locked files on the destination.
       Check replication destination for retention locked files that are in a state that
       is different than the source.
    "
::= { dataDomainMibTraps 5066 }

replDestNotConfigured NOTIFICATION-TYPE
   OBJECTS { replConfigDest }
STATUS current
   DESCRIPTION
   "Description: 
       Destination is not configured, can't initialize
    
   Action: 
       Configure the context on the destination.
    "
::= { dataDomainMibTraps 5067 }

replLagThreshholdReached NOTIFICATION-TYPE
STATUS current
   DESCRIPTION
   "Description: 
       Replication lag threshold reached
    
   Action: 
        Check replication history to make sure replication is properly working.
    "
::= { dataDomainMibTraps 5068 }

replPathTooLong NOTIFICATION-TYPE
STATUS current
   DESCRIPTION
   "Description: 
       Path is too long
    
   Action: 
        Shorten the path.
    "
::= { dataDomainMibTraps 5531 }

sASEnclosureCheck NOTIFICATION-TYPE
STATUS current
   DESCRIPTION
   "Description: 
        Detected that a port has exceeded the maximum limit on the number of supported SAS enclosures.
        Hence, there might be issues with this unsupported configuration.
    
   Action: 
        Read documentation. Inspect the port and reduce the number of externally connected SAS enclosures.
    "
::= { dataDomainMibTraps 5069 }

sASTopologyCheck NOTIFICATION-TYPE
STATUS current
   DESCRIPTION
   "Description: 
        Detected a SAS topology error.
    
   Action: 
        Read documentation.  Verify the connectivity of the SAS enclosures.
    "
::= { dataDomainMibTraps 5070 }

sASPortDisabled NOTIFICATION-TYPE
STATUS current
   DESCRIPTION
   "Description: 
        Detected that an HBA port is disabled.
        Either shelf controller failures or faulty cables.
    
   Action: 
        Contact your contracted support provider or visit us online at https://my.datadomain.com to diagnose a connectivity problem.
    "
::= { dataDomainMibTraps 5071 }

enclosureMixType NOTIFICATION-TYPE
STATUS current
   DESCRIPTION
   "Description: 
        Mix of enclosure type is encountered.
    
   Action: 
        Fix the mix enclosure chain.
    "
::= { dataDomainMibTraps 5528 }

enclosureFwUpgradeAlert NOTIFICATION-TYPE
STATUS current
   DESCRIPTION
   "Description: 
        Enclsoure firmware upgrade failed.
    
   Action: 
        No action required.
    "
::= { dataDomainMibTraps 5534 }

sSLCertificateCorrupted NOTIFICATION-TYPE
STATUS current
   DESCRIPTION
   "Description: 
            The SSL certificate used to establish mutual trust between Data Domain systems is broken.        
        
   Action: 
            Contact your contracted support provider or visit us online at https://my.datadomain.com
        "
::= { dataDomainMibTraps 5072 }

missingSysadminRegistryEntry NOTIFICATION-TYPE
STATUS current
   DESCRIPTION
   "Description: 
        The required registry entry for determining the role of the 'sysadmin' user
        was missing from the registry. This entry is required for the 'sysadmin' user
        to function. Without this, the 'sysadmin' user does not have the proper
        privileges hence cannot perform certain critical/important operations. This
        may cause the system unusable.
        Due to the possible in-correctable consequences this condition may cause,
        DDSH has auto-corrected the issue by adding the missing entry back in the
        registry so the 'sysadmin' user can still function. However, there might
        be issues still if there are other registry entries that are missing.
    
   Action: 
        Contact your contracted support provider or visit us online at https://my.datadomain.com
        to debug why the registry entry for the 'sysadmin' user was missing and
        see if any other registry entries got missing and to fix it.
    "
::= { dataDomainMibTraps 5073 }

smsRestartFullQ NOTIFICATION-TYPE
STATUS current
   DESCRIPTION
   "Description: 
            System management service, SMS is restarted as all service tasks are stuck and not making any progress.
        
   Action: 
            If the problem persist, contact your contracted support provider or visit us online at https://my.datadomain.com.
        "
::= { dataDomainMibTraps 5074 }

mailserverError NOTIFICATION-TYPE
   OBJECTS { systemSerialNumber, alertInfoDescription }
STATUS current
   DESCRIPTION
   "Description: 
            There is a problem communicating with the configured mail server.
            The system will not be able to send out any email notifications that includes alerts, autosupports and daily summary emails.
        
   Action: 
            Make sure that the mail server is configured correctly.
            Verify the configured mail server by sending out a test email from the system.
            If the problem persists, contact your contracted support provider or visit us online at https://my.datadomain.com
        "
::= { dataDomainMibTraps 6511 }

snapshotOver90Percent NOTIFICATION-TYPE
STATUS current
   DESCRIPTION
   "Description: 
        Current number of snapshots for an Mtree is at 90% or more of the maximum number of snapshots allowed.
    
   Action: 
        Consider expiring existing snapshots of that Mtree or adjusting scheduled snapshot retention periods.
    "
::= { dataDomainMibTraps 5075 }

snapshotLimitReached NOTIFICATION-TYPE
STATUS current
   DESCRIPTION
   "Description: 
        Data Domain system has a limit on the number of existing snapshots held at once for a single Mtree.
        Once this limit is reached no more snapshots can be created of that Mtree.
    
   Action: 
        Consider expiring existing snapshots of that Mtree to make room for newer ones.
    "
::= { dataDomainMibTraps 5076 }

sNTZMultipleIterations NOTIFICATION-TYPE
STATUS current
   DESCRIPTION
   "Description: 
    Indicates that sanitization will be run in multiple iterations.
    In the worst case this can take 15-20 days for 280 TBs. It means 
    that the system will not run at full speed for that period of 
    time and that GC will not be run to reclaim space. However, 
    sanitization will also reclaim space back but it might not be 
    as efficient as GC is.

   Action: 
    Make sure that you have enough space to not run out of space and
    that you can wait that many days in the worst case. You should have
    at least 20% of physical space available. Other option is
    to abort sanitization, delete a bunch of files and try again. You can
    do this process iteratively until you do not get this alert anymore. 
"
::= { dataDomainMibTraps 5077 }

coredumpWarning NOTIFICATION-TYPE
STATUS current
   DESCRIPTION
   "Description: 
        /ddvar might soon run out of space to save system core dumps.
    
   Action: 
        Remove unwanted files from /ddvar to free up some space.
        Lack of space can result in missing core dumps that will hamper debugging operations.
    "
::= { dataDomainMibTraps 5078 }

coredumpDisabled NOTIFICATION-TYPE
STATUS current
   DESCRIPTION
   "Description: 
        Space in /ddvar is not sufficient enough for saving system core dumps.
    
   Action: 
        Remove unwanted files from /ddvar to free up some space.
        Lack of space can result in missing core dumps that will hamper debugging operations.
    "
::= { dataDomainMibTraps 5079 }

spaceOver80Percent NOTIFICATION-TYPE
   OBJECTS { fileSystemSpaceUsed }
STATUS current
   DESCRIPTION
   "Description: 
        Space usage has exceeded 80% of the total capacity.
    
   Action: 
        If it is in root or /ddvar, remove unwanted files to free up some space.
        Lack of space can result in missing important logs. 
        If it is in active tier, remove unwanted files to free up some space.
        If it is in archive tier, add more archive units to the filesystem.
    "
::= { dataDomainMibTraps 5080 }

spaceOver90Percent NOTIFICATION-TYPE
   OBJECTS { fileSystemSpaceUsed }
STATUS current
   DESCRIPTION
   "Description: 
        Space usage has exceeded 90% of the total capacity.
    
   Action: 
        If it is in root or /ddvar, remove unwanted files to free up some space.
        Lack of space can result in missing important logs. 
        If it is in active tier, remove unwanted files to free up some space.
        If it is in archive tier, add more archive units to the filesystem.
    "
::= { dataDomainMibTraps 5081 }

diskAccessError NOTIFICATION-TYPE
   OBJECTS { diskSerialNumber }
STATUS current
   DESCRIPTION
   "Description: 
        Data Domain system cannot identify the state of the disk.
    
   Action: 
        Contact your contracted support provider or visit us online at https://my.datadomain.com.
    "
::= { dataDomainMibTraps 5082 }

diskFailure NOTIFICATION-TYPE
   OBJECTS { diskSerialNumber }
STATUS current
   DESCRIPTION
   "Description: 
        The disk is in one of the following states: absent, failed, foreign.
    
   Action: 
        Make sure that the disk is securely connected.
        If the disk has gone bad then it needs a replacement.
    "
::= { dataDomainMibTraps 5083 }

diskTemperatureWarning NOTIFICATION-TYPE
   OBJECTS { diskTemperature }
STATUS current
   DESCRIPTION
   "Description: 
        The disk temperature sensor reading has exceeded the warning threshold.
    
   Action: 
        If the temperature is high due to high activity for a short period, it should return
        to normal later. If not, check if there is any fan failure or if the surrounding
        environment temperature is too high or too low or if the sensor is reporting
        inaccurate value.
    "
::= { dataDomainMibTraps 5084 }

diskTemperatureShutdown NOTIFICATION-TYPE
   OBJECTS { diskTemperature }
STATUS current
   DESCRIPTION
   "Description: 
        The disk temperature sensor reading has exceeded the critical threshold.
    
   Action: 
        The system will shut down for this high temperature critical alert.
        Check if there is any fan failure or if the surrounding environment temperature is too
        high or too low or if the sensor is reporting inaccurate value.
    "
::= { dataDomainMibTraps 5085 }

unsupportedHardwareSpareSize NOTIFICATION-TYPE
   OBJECTS { diskSerialNumber }
STATUS current
   DESCRIPTION
   "Description: 
        The disk capacity is too small for it to be of any use in the system.
    
   Action: 
        Replace with a larger capacity disk.
    "
::= { dataDomainMibTraps 5086 }

missingDiskGroup NOTIFICATION-TYPE
STATUS current
   DESCRIPTION
   "Description: 
        One or more critical disks/LUNs are unavailable.
    
   Action: 
        Make sure all storage is securely connected.
        Look at alert history for any path failures.
        Check for any core files, a critical layer may be unavailable.
        Verify that all storage is working and recognized correctly.
    "
::= { dataDomainMibTraps 5087 }

diskGroupReconstructionNoProgress NOTIFICATION-TYPE
STATUS current
   DESCRIPTION
   "Description: 
        One or more disks are failed and the RAID reconstruction is not running.
    
   Action: 
        Make sure there is/are spare disk(s) in the system.
    "
::= { dataDomainMibTraps 5088 }

diskGroupReconstruction NOTIFICATION-TYPE
STATUS current
   DESCRIPTION
   "Description: 
        Two or more disks are failed and the RAID protection is in critical state.
        If an additional disk fails, there might be permanent loss of data.
        The system will shut down if the problem is not fixed.
    
   Action: 
        Make sure there is/are spare disk(s) in the system.
    "
::= { dataDomainMibTraps 5089 }

diskGroupReconstructionShutdown NOTIFICATION-TYPE
STATUS current
   DESCRIPTION
   "Description: 
        Two or more disks are failed and the RAID protection is in critical state for over a
        considerable period of time. If an additional disk fails, there might be permanent loss of
        data. The system will shut down.
    
   Action: 
        Restart the system and make sure there is/are spare disk(s) in the system.
    "
::= { dataDomainMibTraps 5090 }

diskGroupReconstructionCritical NOTIFICATION-TYPE
STATUS current
   DESCRIPTION
   "Description: 
        Two or more disks are failed and the RAID protection is in critical state for over a
        considerable period of time. If an additional disk fails, there might be permanent loss of
        data.
    
   Action: 
        Make sure there is/are spare disk(s) in the system.
    "
::= { dataDomainMibTraps 5091 }

diskUnknown NOTIFICATION-TYPE
STATUS current
   DESCRIPTION
   "Description: 
        Disk is unknown.
    
   Action: 
        Add disk to the system.
    "
::= { dataDomainMibTraps 5092 }

enclUnknown NOTIFICATION-TYPE
STATUS current
   DESCRIPTION
   "Description: 
        All disks in enclosure are unknown.
    
   Action: 
        Add enclosure to the system.
    "
::= { dataDomainMibTraps 5093 }

lowSpares NOTIFICATION-TYPE
STATUS current
   DESCRIPTION
   "Description: 
        Not enough spare disks can be detected for this tier.
        There may be failed disks or connectivity issues with disks or enclosures.
    
   Action: 
        Replace any failed or absent disks. Check enclosure connectivity.
    "
::= { dataDomainMibTraps 5094 }

unsupportedConfigurationROL NOTIFICATION-TYPE
STATUS current
   DESCRIPTION
   "Description: 
        Raid on LUN from 4.8 is no longer supported.  Please follow instruction on how to increase 
        usable space in your filesystem. 
    
   Action: 
                1) migrate data away 
                2) do a filesystem destroy
                3) add your LUN
                4) migrate data back  
    "
::= { dataDomainMibTraps 5095 }

syslogAlert NOTIFICATION-TYPE
STATUS current
   DESCRIPTION
   "Description: 
A message of high severity has been logged.

   Action: 
Look at the logs and check if there is a problem that needs attention.
"
::= { dataDomainMibTraps 5096 }

vTLFCLinkOffline NOTIFICATION-TYPE
   OBJECTS { vtlPortTrapIndex }
STATUS current
   DESCRIPTION
   "Description: 
        VTL FC Link is offline: Port %s 
    
   Action: 
        If this port is not in use, please disable it. If port is being
        used, please check FC Port connectivity. Alert will be cleared
        when port is disabled or online.
    "
::= { dataDomainMibTraps 5529 }

vTLFCLinkOscillations NOTIFICATION-TYPE
STATUS current
   DESCRIPTION
   "Description: 
        VTL-FCMON: Number of link oscillations for VTL FC Port %s = %d,
        in a time interval of %d minutes. Current threshold is %d.
    
   Action: 
        Check FC Port connectivity. Please disable the port if it is not in use.
    "
::= { dataDomainMibTraps 5530 }

vTLFCLinkOnline NOTIFICATION-TYPE
   OBJECTS { systemSerialNumber, vtlPortTrapIndex }
STATUS current
   DESCRIPTION
   "Description: 
         VTL FC Link is online: Port %s
    
   Action: 
        No Action required.
    "
::= { dataDomainMibTraps 5097 }

END
